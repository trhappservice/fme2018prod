FME workspace Maximo_Create_Comments.fmw

Parameters:
- SourceDataset_TEXTLINE_SF_Comments = U:\2017-07 Maximo-FME\2017-08-29\Start of Day\CanonicalCommentForMaximo.txt
- MaximoServiceUrl = http://wamsif.richmondhill.ca/meaweb/services   # Maximo Server URL

Readers:
- TEXTLINE_1: TEXTLINE from $(SourceDataset_TEXTLINE_SF_Comments)

Note: Update queue with JobId, Process_Date
SQLExecutor_2
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER ;
      UPDATE dbo.[fme_comment_queue]
      SET [job_id] = $(FME_JOB_ID), [process_date] = CURRENT_TIMESTAMP, [status] = 'InProgress'
      WHERE [comment_id]  = '@Value(Comment.Id)' AND [status] = 'Pending';
    INITIATOR -> IsNotDeleted
    <REJECTED> -> Terminator
IsNotDeleted: Tester
    BOOL_OP = OR
    TEST_CLAUSE = TEST @Value(Comment.IsDeleted) NOT_= true
    PASSED -> XMLTemplater_3 [ROOT]
Note: Delete from queue
SQLExecutor
    COMBINE_ATTRS = Result Attributes Only
    COMBINE_GEOM = Initiator Geometry Only
    DATASET = TWV-SQL3_QueueDB
    EXPOSED_ATTRIBUTE_LIST = salesforce_id
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER ;
      DELETE FROM dbo.[fme_comment_queue]
      WHERE [comment_id] = '@Value(Comment.Id)' AND [status] = 'InProgress';
    <REJECTED> -> Terminator_2
Terminator_2
    MESSAGE = Translation Terminated: SQL Executor Failed
Terminator
    MESSAGE = Translation Terminated: SQL Executor Failed

Bookmark: Read SF Comments Data
text_line (reader TEXTLINE_1)
    attributes: text_line_data buffer
    -> StringReplacer
StringReplacer
    CASE = NO
    FIND_TEXT = &
    NO_MATCH = _FME_NO_OP_
    REGEXP = NO
    REPLACE_TEXT = &amp;
    SRC_ATTRS = text_line_data
    -> JSONTemplater [ROOT]
Note: Read SF Comments Data
JSONTemplater
    RESULT_ATTRIBUTE = _result
    ROOT_QUERY_EXPR = @Value(text_line_data)
    VISIBLE_QUERY_VALIDATE = Yes
    -> JSONFlattener
JSONFlattener
    ERROR_LIST_ATTR = _json_error
    JSON_DOCUMENT = @Value(_result)
    NEW_ATTRIBUTES = Source_Request_Id Target_Request_Id Comment.Description Comment.CreateDate Comment.IsDeleted Comment.IsPublic Comment.Id
    READ_FROM_FILE = NO
    RECURSIVE = Yes
    -> JSONFlattener_Output
    -> AttributeCreator
JSONFlattener_Output: Logger
    LOG_FEATURE = LOG_RECORD
    MAXCOORDS = 20
    MAXFEATS = 20
    MESSAGE = Feature is: Input Canonical Data
    SEVERITY = INFO

Bookmark: Rename and Format Date Attribute
Note: First 30 CHAR of Comments fo rDescription
AttributeCreator
    ATTR_TABLE:
      SET_TO WORKLOG.DESCRIPTION = @Left(@Value(Comment.Description),30)
      SET_TO WORKLOG.DESCRIPTION_LONGDESCRIPTION = @Value(Comment.Description)
      SET_TO WORKLOG.CREATEDATE = @Value(Comment.CreateDate)
    -> SQLExecutor_2 [INITIATOR]

Bookmark: Insert Comments in Maximo
Note: Call UpdateTRHFMESR webservice
XMLTemplater_3
    OUTPUT_XML_HEADER = Yes
    RESULT_ATTRIBUTE = Insert_Comments
    ROOT_QUERY_EXPR:
      <soapenv:Envelope xmlns:soapenv="http://schemas.xmlsoap.org/soap/envelope/" xmlns:max="http://www.ibm.com/maximo">
         <soapenv:Header/>
         <soapenv:Body>
      	<max:UpdateTRHFMESR>
        	   <max:TRHFMESRSet>
        	   <max:SR action="Change">

                <max:CLASS>SR</max:CLASS>
      	      <max:TICKETID>{fme:get-attribute("Target_Request_Id")}</max:TICKETID>
      	      <max:ORGID>TRH</max:ORGID>
      	      <max:SITEID>WAMS</max:SITEID>
      	      <max:TRHFMEREQUESTID>{fme:get-attribute("Source_Request_Id")}</max:TRHFMEREQUESTID>

                  <max:WORKLOG>
                      <max:CLIENTVIEWABLE>1</max:CLIENTVIEWABLE>
                      <max:DESCRIPTION>{fme:get-attribute("WORKLOG.DESCRIPTION")}</max:DESCRIPTION>
                      <max:DESCRIPTION_LONGDESCRIPTION>{fme:get-attribute("WORKLOG.DESCRIPTION_LONGDESCRIPTION")}</max:DESCRIPTION_LONGDESCRIPTION>
                      <max:LOGTYPE>CLIENTNOTE</max:LOGTYPE>
                  </max:WORKLOG>
      	    </max:SR>
      	  </max:TRHFMESRSet>
      	</max:UpdateTRHFMESR>
      </soapenv:Body>
      </soapenv:Envelope>
    VISIBLE_QUERY_VALIDATE = Yes
    -> XMLFormatter_2
XMLFormatter_2
    COLLAPSE_EMPTY_ELEMENT = Yes
    FORMATTING_CHOICE = Pretty-Print XML
    INDENT_SIZE = 1
    LIST_NAME = _xml_error
    NAMESPACE_CLEANUP = No
    OUTPUT_ENCODING = utf-8
    REMOVE_ALL_COMMENT = Yes
    REMOVE_EMPTY_ELEMENT = Yes
    REPLACE_TABS_WITH_SPACES = no
    SCHEMALOC_CLEANUP = No
    TEXT_INDENT = no
    WHITESPACE_HANDLING = Preserve all whitespace
    XML_ATTR_TEXT = Insert_Comments
    XML_INPUT_TYPE = Attribute Specifying XML Text
    XML_OUTPUT_ATTR = UpdateSRXML
    XML_OUTPUT_TYPE = Attribute
    PASSED -> HTTPCaller_3
HTTPCaller_3
    AUTH_METHOD = Web Connection
    AUTH_NAMED_CONNECTION = Maximo
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(MaximoServiceUrl)/TRHFMESYS_TRHFMESRUPDATEES
    TRANSFER_TIMEOUT_LENGTH = 90
    UPLOAD_BODY = @Value(UpdateSRXML)
    UPLOAD_CONTENT_TYPE = text/xml
    UPLOAD_TYPE = Specify Upload Body
    USE_COOKIES = No
    VERIFY_SSL_CERTIFICATES = No
    -> HTTPCaller_3_Output
HTTPCaller_3_Output: Logger
    LOG_FEATURE = LOG_RECORD
    MAXCOORDS = 20
    MAXFEATS = 20
    MESSAGE = Feature is: Output Canonical Data
    SEVERITY = INFO
    LOGGED -> SQLExecutor [INITIATOR]
