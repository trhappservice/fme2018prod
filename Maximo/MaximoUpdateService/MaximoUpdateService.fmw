FME workspace MaximoUpdateService.fmw

Parameters:
- SourceDataset_TEXTLINE = MaximoUpdate   # Source Text File(s)
- TrafficOpsRegulatorySigns = Regulatory Road Sign Issues   # Enter the text for regulatory traffic signs
- TrafficOpsNonRegulatorySigns = Non-Regulatory Road Sign Issues   # Enter text for non-regulatory road signs case type
- MaximoServiceUrl = http://wamsif.richmondhill.ca/meaweb/services   # Maximo Server URL
- SERVER_CONNECTION = FME Server   # "FME Server" Connection

Readers:
- TEXTLINE_1: TEXTLINE from $(SourceDataset_TEXTLINE)

Terminator_4
    MESSAGE = @Value(_reader_error)
Note: AttributeRemover : Output
Junction_12
    -> isNewServiceRequest
isNewServiceRequest: Tester
    BOOL_OP = OR
    TEST_CLAUSE = TEST @Value(isNew) = true
    PASSED -> Emailer_2
    PASSED -> NewSR_Templater [ROOT]
    FAILED -> IsClosed
Emailer_2 [off]
    ATTACHGROUP = No
    BODY:
      Before Going to XML

      Max Schedstart: @Value(MX_SCHEDSTART)


      Total Response Time: @Value(SR_QA.Total_Response_Time)
    FROM = noreply@richmondhill.ca
    SERVICE = Generic SMTP
    SMTP_CONNECTION = HOST;relay.richmondhill.local;PORT;25;ENCRYPTION;None;TIMEOUT;60;AUTHENTICATION;NO;USERNAME;<Unused>;PASSWORD;<Unused>;FME_CONTROLLER_QUERY_FILE;transformers\dependencies\emailer\Generic SMTP.fme
    SUBJECT = MAX SCHEDSTART
    TO = jimmy.chao@richmondhill.ca
Terminator_6
    MESSAGE = Translation Terminated
Emailer_3 [off]
    ATTACHGROUP = No
    BODY = "@Value(SR_QA.Total_Response_Time)\n"
    FROM = noreply@richmondhill.ca
    SERVICE = Generic SMTP
    SMTP_CONNECTION = HOST;relay.richmondhill.local;PORT;25;ENCRYPTION;None;TIMEOUT;60;AUTHENTICATION;NO;USERNAME;<Unused>;PASSWORD;<Unused>;FME_CONTROLLER_QUERY_FILE;transformers\dependencies\emailer\Generic SMTP.fme
    SUBJECT = MAX Total Reponse Time
    TO = jimmy.chao@richmondhill.ca

Bookmark: 1. Parse Canonical Model
  Flatten the incoming JSON format into a set of attributes and expose these for use in the workflow.
text_line (reader TEXTLINE_1)
    attributes: text_line_data buffer
    -> TopicFlattener
Note: Confirm if this is a new / request or not
Note: Convert topic content to JSON
TopicFlattener: JSONFlattener
    ERROR_LIST_ATTR = _json_error
    JSON_DOCUMENT = @Value(text_line_data)
    NEW_ATTRIBUTES = ws_topic opt_topic
    READ_FROM_FILE = NO
    RECURSIVE = Yes
    -> AttributeExposer
    -> Junction
Note: Expose attributes of the / canonical service request
AttributeExposer
    ATTR_LIST = Address,Asset_Id,AssignedGroup,Block_Id,CloseReason,ClosedComments,Contact.AddressCity,Contact.AddressCountry,Contact.AddressPostalCode,Contact.AddressProvince,Contact.AddressStreet,Contact.AddressSuite,Contact.Email,Contact.FirstName,Contact.HomePhone,Contact.LastName,Contact.OtherPhone,Description,OnHoldStatusReason,Owner,Parent_Id,RequestNumber,SR_QA.Preferred_Appliance_Pickup_Date,SR_QA.Acceptable_Metal_Items,SR_QA.Activity_Type,SR_QA.Cause_of_Damage,SR_QA.Duration_of_Work,SR_QA.Enter_Type_of_Dead_Animal,SR_QA.For_Fire_Request_Work_Order,SR_QA.Location_of_Damage,SR_QA.Name_of_Contractor_Utility,SR_QA.Other_Appliance_Question,SR_QA.Size_of_Pothole,SR_QA.Type_of_Appliance,SR_QA.Type_of_Dumped_Item,SR_QA.Type_of_Item_Missed,SR_QA.Type_of_Truck,SR_QA.What_Was_Damaged,ServiceLocation.Address,ServiceLocation.City,ServiceLocation.Country,ServiceLocation.Details,ServiceLocation.FormattedAddress,ServiceLocation.Latitude,ServiceLocation.Longitude,ServiceLocation.Parcel_Id,ServiceLocation.PostalCode,ServiceLocation.Province,ServiceLocation.Suite,Source_Request_Id,Status,Subject,Target_AssignedTo,Target_Request_Id,Type,SR_QA.Appointment_Date,SR_QA.Appointment_Time,SR_QA.Type_of_Emergency,SR_QA.Total_Response_Time
    -> Junction_3
    -> SQLExecutor_3 [INITIATOR]
    -> Emailer_3
Note: Confirm if this is a new / request or not
CreateIsNewFlag: AttributeCreator
    ATTR_TABLE = SET_TO isNew = FME_CONDITIONAL:DEFAULT_VALUE'true'BOOL_OP;AND;COMPOSITE_TEST;<Unused>;TEST @Value(Target_Request_Id) ATTRIBUTE_HAS_VALUE _FME_BLANK_STRING_;TEST @Value(Target_Request_Id) NOT_= null;TEST Target_Request_Id NOT_ATTRIBUTE_VALUE_NULL _FME_BLANK_STRING_'false'FME_NUM_CONDITIONS2___
    -> Junction_5
Note: Step #2: FieldMapper
Junction_5
    -> Junction_6
Note: Log Outputs: ReceivedSR
Junction_3
    -> Junction_4
Note: Log Outputs: TopicFlattener
Junction
    -> Junction_2

Bookmark: Message Queue - Update InProgress
SQLExecutor_3
    COMBINE_ATTRS = Keep Initiator Attributes if Conflict
    COMBINE_GEOM = Initiator Geometry Only
    DATASET = TWV-SQL3_QueueDB
    EXPOSED_ATTRIBUTE_LIST = row_count
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER ;
      UPDATE dbo.[fme_case_queue]
      SET [job_id] = $(FME_JOB_ID), [status] = 'InProgress', [process_date] = CURRENT_TIMESTAMP
      WHERE dbo.[fme_case_queue].[salesforce_id] = '@Value(Source_Request_Id)' AND dbo.[fme_case_queue].[status] = 'Pending';
    INITIATOR -> CreateIsNewFlag
    <REJECTED> -> Logger
Logger
    LOG_FEATURE = LOG_ONLY
    MAXCOORDS = 20
    MAXFEATS = 20
    MESSAGE = SQL Executor Error
    SEVERITY = ERROR
    LOGGED -> Terminator_4

Bookmark: 2. Map Canonical to Maximo
  Some of the field mapping requires concatenation of fields
Note: CreateIsNewFlag : Output
Junction_6
    -> FieldMapper
Note: CanonicalMapping.xls contains basic / mapping. Additional logic added.
FieldMapper: AttributeManager
    ATTR_TABLE:
      REMOVE text_line_data
      REMOVE ws_topic
      REMOVE opt_topic
      REMOVE Address
      RENAME_SET_VALUE Asset_Id > TRH_ASSETNUM
      SET_TO TRH_BLOCK = @PadLeft(@Value(Block_Id),2,0)
      RENAME_SET_VALUE Contact.Email > TRHEMAIL
      RENAME_SET_VALUE Contact.FirstName > TRHFIRSTNAME
      RENAME_SET_VALUE Contact.HomePhone > TRHPHONENUMBER
      RENAME_SET_VALUE Contact.LastName > TRHLASTNAME
      RENAME_SET_VALUE Contact.OtherPhone > TRHCELLNUMBER
      RENAME_SET_VALUE OnHoldStatusReason > NP_STATUSMEMO
      RENAME_SET_VALUE Owner > OWNER
      RENAME_SET_VALUE Parent_Id > GLOBALTICKETID
      RENAME_SET_VALUE ServiceLocation.Address > TKSERVICEADDRESS.STREETADDRESS
      RENAME_SET_VALUE ServiceLocation.City > TKSERVICEADDRESS.CITY
      RENAME_SET_VALUE ServiceLocation.Country > TKSERVICEADDRESS.COUNTRY
      RENAME_SET_VALUE ServiceLocation.Latitude > TKSERVICEADDRESS.LATITUDEY
      RENAME_SET_VALUE ServiceLocation.Longitude > TKSERVICEADDRESS.LONGITUDEX
      REMOVE ServiceLocation.Parcel_Id
      RENAME_SET_VALUE ServiceLocation.PostalCode > TKSERVICEADDRESS.POSTALCODE
      RENAME_SET_VALUE ServiceLocation.Province > TKSERVICEADDRESS.STATEPROVINCE
      RENAME_SET_VALUE ServiceLocation.Suite > TKSERVICEADDRESS.ADDRESSLINE2
      RENAME_SET_VALUE Source_Request_Id > TRHFMEREQUESTID
      RENAME_SET_VALUE Status > STATUS
      RENAME_SET_VALUE Target_AssignedTo > OWNER
      RENAME_SET_VALUE Target_Request_Id > TICKETID
      SET_TO DESCRIPTION = [@Value(RequestNumber)] @Value(Type): @Value(Subject)
      SET_TO DESCRIPTION_LONGDESCRIPTION = @Value(Description)

        QUESTIONS AND ANSWERS
        Type of Truck: @Value(SR_QA.Type_of_Truck)
        Type of Dumped Item: @Value(SR_QA.Type_of_Dumped_Item)
        Type of Appliance: @Value(SR_QA.Type_of_Appliance)
        Acceptable Metal Items: @Value(SR_QA.Acceptable_Metal_Items)
        Preferred Appliance Pickup Date: @Value(SR_QA.Preferred_Appliance_Pickup_Date)
        Type of Item Missed: @Value(SR_QA.Type_of_Item_Missed)
        What Was Damaged: @Value(SR_QA.What_Was_Damaged)
        Cause of Damage: @Value(SR_QA.Cause_of_Damage)
        Type of Dead Animal: @Value(SR_QA.Enter_Type_of_Dead_Animal)
        Size of Pothole: @Value(SR_QA.Size_of_Pothole)
        Duration of Work: @Value(SR_QA.Duration_of_Work)
        Name of Contractor Utility: @Value(SR_QA.Name_of_Contractor_Utility)
        Location of Damage: @Value(SR_QA.Location_of_Damage)
        Activity Type: @Value(SR_QA.Activity_Type)
        Appointment Date: @Value(SR_QA.Appointment_Date)
        Appointment Time: @Value(SR_QA.Appointment_Time)
        Type of Emergency: @Value(SR_QA.Type_of_Emergency)
        Fire Request Work Order: @Value(SR_QA.For_Fire_Request_Work_Order)

      SET_TO TRHCALLERADDRESS = @UpperCase(@Value(Contact.AddressStreet)  @Value(Contact.AddressSuite) @Value(Contact.AddressCity)  @Value(Contact.AddressProvince)  @Value(Contact.AddressPostalCode))
      RENAME_SET_VALUE ServiceLocation.Details > TRHDIRECTIONS
      RENAME_SET_VALUE RequestNumber > TRHCRMCASEID
      REMOVE ServiceLocation.FormattedAddress
      SET_TO TKSERVICEADDRESS.FORMATTEDADDRESS = @Value(TKSERVICEADDRESS.STREETADDRESS) @Value(TKSERVICEADDRESS.CITY) @Value(TKSERVICEADDRESS.STATEPROVINCE)  @UpperCase(@Value(TKSERVICEADDRESS.POSTALCODE))
      SET_TO TKSERVICEADDRESS.DIRECTIONS = @Trim(@Value(TKSERVICEADDRESS.STREETADDRESS) @Value(TKSERVICEADDRESS.ADDRESSLINE2))
    -> Junction_7
    -> CreateMaxScheudleStart
CreateMaxScheudleStart: AttributeCreator
    ATTR_TABLE = SET_TO MX_SCHEDSTART = FME_CONDITIONAL:DEFAULT_VALUE''BOOL_OP;AND;COMPOSITE_TEST;<Unused>;TEST @Value(SR_QA.Appointment_Time) = A.M.'@Value(SR_QA.Appointment_Date) 8:30:00'BOOL_OP;OR;COMPOSITE_TEST;<Unused>;TEST @Value(SR_QA.Appointment_Time) = P.M.'@Value(SR_QA.Appointment_Date) 13:00:00'FME_NUM_CONDITIONS3___
    -> AttributeValueMapper
Note: Map STATUS to either / CLOSED, PENDING, or NULL
AttributeValueMapper
    DEFAULT_VALUE = FME_NULL_VALUE
    DIRECTION = Forward (Source To Destination)
    LUT = Closed,CLOSED,Pending,PENDING
    SRC = STATUS
    VAL_ATTR = STATUS
    -> WorkGrpMapper
Note: Map Maximo Values to / TRH_OWNERGROUP
WorkGrpMapper: AttributeValueMapper
    DIRECTION = Forward (Source To Destination)
    LUT = TRH_Waste_Management,PARKS,TRH_Urban_Forestry_Trees,FORESTRY,TRH_Parks,PARKS,TRH_Roads_Spring_Summer_Fall,ROADS,TRH_Roads_Winter,ROADS,TRH_Asset_Management,AM,TRH_Waste_Water,WWW,TRH_Water_Account,WWW,Water_Wastewater,WWW
    SRC = AssignedGroup
    VAL_ATTR = TRH_OWNERGROUP
    -> Junction_25
    -> If_TrafficOps
Note: Check if the case type is for / road signs. Assigned to TRAFFIC
If_TrafficOps: Tester
    BOOL_OP = OR
    TEST_CLAUSE:
      TEST @Value(Type) = $(TrafficOpsNonRegulatorySigns)
      TEST @Value(Type) = $(TrafficOpsRegulatorySigns)
    PASSED -> TrafficSetter
    FAILED -> AMPriorityTester
Note: Set TRH_OWNERGROUP=TRAFFIC
TrafficSetter: AttributeCreator
    ATTR_TABLE = SET_TO TRH_OWNERGROUP = TRAFFIC
    -> AMPriorityTester
Note: Check if the Maximo Division / is for Asset Management
AMPriorityTester: Tester
    BOOL_OP = OR
    TEST_CLAUSE = TEST @Value(TRH_OWNERGROUP) = AM
    PASSED -> AMPriorityMapper
    FAILED -> AttributeCreator
Note: Set the AM Priority / for Asset Management
AMPriorityMapper: AttributeCreator
    ATTR_TABLE:
      SET_TO TRHAMPRIORITY = @Value(Type)
      SET_TO DESCRIPTION = [@Value(TRHCRMCASEID)] @Value(Subject)
    -> AttributeCreator
AttributeCreator
    ATTR_TABLE = SET_TO CaseTypeLookup = @Value(TRH_OWNERGROUP).@Trim(@Value(Type))
    -> JobMapper
Note: Map Case Type to / Maximo Job Number
JobMapper: AttributeValueMapper
    DIRECTION = Forward (Source To Destination)
    LUT = AM.Priority Repair,JP4055,AM.Routine Repair,JP4055,AM.Urgent Repair,JP4055,PARKS. Winter - Property Damage from Sidewalk Plows,JP3061,PARKS.Additional Equipment or Signs,JP3062,PARKS.Courts and Field Maintenance,JP3090,PARKS.Curbside Special Request,JP3115,PARKS.Driver Feedback,JP3115,PARKS.Dumped Garbage,JP3115,PARKS.Flooding in a Park,JP3062,PARKS.Garbage Maintenance,JP3115,PARKS.Graffiti in a Park,JP3062,PARKS.Grass Cutting ,JP3062,PARKS.Horticulture Maintenance,JP3089,PARKS.Insect Problem in a Park,JP3062,PARKS.Large Appliances,JP3115,PARKS.Lighting Maintenance Required,JP3062,PARKS.Missed Collection,JP3115,PARKS.Multi Residential,JP3115,PARKS.Playground Equipment Maintenance,JP3066,PARKS.Special Investigation,JP3062,PARKS.Splash Pad Maintenance,JP3066,PARKS.Washroom Maintenance,JP3062,PARKS.Wildlife Concern,JP3062,PARKS.Winter - Sidewalk Plow Driver Complaint,JP3060,PARKS.Winter Maintenance,JP3060,PARKS.Winter Sidewalk Maintenance,JP3060,TRAFFIC.Non-Regulatory Road Sign Issues,JP4053,TRAFFIC.Regulatory Road Sign Issues,JP4053,ROADS.Catch Basin - Requires Maintenance,JP4051,ROADS.Catch Basin - Snow or Debris Covered/Flooded,JP4051,ROADS.Culvert Issues,JP4051,ROADS.Dead Wildlife on Road,JP4051,ROADS.Garbage on the Road,JP4051,ROADS.Inspection Request,JP4051,ROADS.Malfunctioning Traffic Signal or Outages,JP4051,ROADS.Pavement Markings and Line Painting,JP4051,ROADS.Pothole,JP4051,ROADS.Road Occupancy Permit,JP4052,ROADS.Road Sweeping in Construction Areas,JP4051,ROADS.Sidewalk & Curb Maintenance,JP4051,ROADS.Sod or Property Damage Caused by Utility Company,JP4051,ROADS.Stormwater Pond Maintenance,JP4051,ROADS.Street Light Locates,JP4051,ROADS.Street Sweeping,JP4051,ROADS.Streetlight Maintenance Reporting,JP4051,ROADS.Windrow Complaint,JP4051,ROADS.Windrow Application Inquiry,JP4051,ROADS.Winter - Courts and Cul-de-Sacs,JP4051,ROADS.Winter - Property Damage from Snow Plows,JP4051,ROADS.Winter - Snow Plow Driver Complaint,JP4051,PARKS.Winter - Sod Damage,JP3061,ROADS.Winter - Street Not Plowed,JP4051,ROADS.Winter - Street Not Salted,JP4051,ROADS.Winter - Wide Bend,JP4051,FORESTRY.Branch Clean Up,JP100131,FORESTRY.Damaged Tree - Accident Related,JP100131,FORESTRY.Damaged Tree - Storm Related,JP100131,FORESTRY.High Priority,JP100131,FORESTRY.Insect Related,JP100131,FORESTRY.Inspection Request,JP100131,FORESTRY.Park/Open Space - High Priority,JP100131,FORESTRY.Parks/Open Space - Inspection Request,JP100131,FORESTRY.Planting Request,JP100131,FORESTRY.Routine Pruning,JP100131,FORESTRY.Surface Roots Maintenance Required,JP100131,WWW.Curb Box Adjustment,JP3152,WWW.Emergency Service Request,JP3152,WWW.Spills,JP4283,WWW.General Inspection Request,JP3152,WWW.Water Off/On Appointment,JP3153,WWW.Water Pressure/Quality,JP3154,WWW.Hydrant Meter Installation/Removal,JP3155,WWW.Compliance Inquiry,JP4526,WWW.Infill Services,JP4525,WWW.Sewer Inquiry,JP4523,WWW.Hydrant Flow Test,JP4524
    SRC = CaseTypeLookup
    VAL_ATTR = JPNUM
    -> PythonNullRemover
Note: Remove NULL values from Case / Q&A Fields in LONGDESCRIPTION
PythonNullRemover: PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              txtDescription = feature.getAttribute("DESCRIPTION_LONGDESCRIPTION").split("\n")    #split the string into a list at newline characters
              startIndex = txtDescription.index("QUESTIONS AND ANSWERS")                          #look for the 'QUESTION AND ANSWERS' section and retrieve the index
              txtCallerAddress = feature.getAttribute("TRHCALLERADDRESS")
              txtFormattedAddress = feature.getAttribute("TKSERVICEADDRESS.FORMATTEDADDRESS")

              txtOut=txtDescription[0]                                    #write out first line of text
              for i in range(1, len(txtDescription)-1):                   #iterate over each line
                  if i > startIndex:                                      #for strings following 'QUESTIONS AND ANSWERS'
                      tokenString = txtDescription[i].split(":")          #split each string at colon ':'
                      if tokenString[1].strip() != "":                    #if the question contains an answer then
                          txtOut = txtOut + "<br/>" + txtDescription[i]      #write the answer to output string
                  elif i == startIndex:
                      txtOut = txtOut + "<br/><b>" + txtDescription[i] + "</b>"
                  else:
                     txtOut = txtOut + "<br/>" + txtDescription[i]           #write first few lines before 'QUESTIONS AND ANSWERS'

              feature.setAttribute("DESCRIPTION_LONGDESCRIPTION",txtOut)  #overwrite the LONGDESCRIPTION field with recalculated string
              feature.setAttribute("TKSERVICEADDRESS.FORMATTEDADDRESS", txtFormattedAddress.strip())
              feature.setAttribute("TRHCALLERADDRESS", txtCallerAddress.strip())
              self.pyoutput(feature)
          def close(self):
              pass
    PYTHONSYMBOL = FeatureProcessor
    -> AttributeReprojector
Note: Project problem location / to UTM Zone 17N
AttributeReprojector
    DEST = UTM84-17N
    SOURCE = LL84
    XATTR = TKSERVICEADDRESS.LONGITUDEX
    YATTR = TKSERVICEADDRESS.LATITUDEY
    -> AttributeRemover
AttributeRemover
    REMOVE_ATTRS = SR_QA.Other_Appliance_Question,SR_QA.Type_of_Dumped_Item,SR_QA.Preferred_Appliance_Pickup_Date,Type,Subject,Description,SR_QA.What_Was_Damaged,Contact.AddressStreet,SR_QA.Type_of_Appliance,SR_QA.Cause_of_Damage,Contact.AddressCity,SR_QA.Acceptable_Metal_Items,SR_QA.Enter_Type_of_Dead_Animal,SR_QA.Type_of_Item_Missed,SR_QA.Duration_of_Work,SR_QA.Type_of_Truck,SR_QA.Activity_Type,SR_QA.Size_of_Pothole,Contact.AddressPostalCode,SR_QA.Location_of_Damage,SR_QA.For_Fire_Request_Work_Order,SR_QA.Name_of_Contractor_Utility,Contact.AddressProvince,Contact.AddressCountry,Contact.AddressSuite
    -> AssetNumTester
Note: Check if park or facility / LOCATION is specified and that / ASSETNUM is specified for right / division, else set to NULL
AssetNumTester: TestFilter
    DEFAULT_VALUE = <UNFILTERED>
    TEST_LIST:
      BOOL_OP,OR,COMPOSITE_TEST,<Unused>,TEST_CLAUSE,"TEST @Value(TRH_ASSETNUM) BEGINS_WITH PK-
      TEST @Value(TRH_OWNERGROUP) = AM",PARKS or AM,BOOL_OP,AND,COMPOSITE_TEST,<Unused>,TEST_CLAUSE,"TEST @Value(TRH_ASSETNUM) BEGINS_WITH FL
      TEST @Value(TRH_OWNERGROUP) = AM",FACILITY LIGHTS,BOOL_OP,AND,COMPOSITE_TEST,<Unused>,TEST_CLAUSE,"TEST @Value(TRH_ASSETNUM) BEGINS_WITH TR_
      TEST @Value(TRH_OWNERGROUP) = FORESTRY",FORESTRY TREES,BOOL_OP,AND,COMPOSITE_TEST,<Unused>,TEST_CLAUSE,"TEST @FindRegEx(@Value(TRH_ASSETNUM),^\d{2}-\d{4}) != -1
      TEST @Value(TRH_OWNERGROUP) = ROADS",STREET LIGHTS
    PARKS or AM -> LocationSetter
    FACILITY LIGHTS -> Junction_11
    FORESTRY TREES -> Junction_11
    STREET LIGHTS -> Junction_11
    <UNFILTERED> -> NullSetter
Note: Remove Service Address and / Rename Asset Id to Location
LocationSetter: AttributeManager
    ATTR_TABLE:
      RENAME_SET_VALUE TRH_ASSETNUM > LOCATION
      REMOVE TKSERVICEADDRESS.STREETADDRESS
      REMOVE TKSERVICEADDRESS.CITY
      REMOVE TKSERVICEADDRESS.COUNTRY
      REMOVE TKSERVICEADDRESS.POSTALCODE
      REMOVE TKSERVICEADDRESS.STATEPROVINCE
      REMOVE TKSERVICEADDRESS.ADDRESSLINE2
      REMOVE TKSERVICEADDRESS.FORMATTEDADDRESS
      REMOVE TKSERVICEADDRESS.DIRECTIONS
    -> Junction_11
    -> Junction_9
Note: Set TRH_ASSETNUM to Null / if it doesn't match rules
NullSetter: AttributeCreator
    ATTR_TABLE = SET_TO TRH_ASSETNUM = FME_NULL_VALUE
    -> Junction_11
    -> Junction_9
Note: isNewServiceRequest : Input
Junction_11
    -> Junction_12
Note: StepTwo_Log : Input
Junction_9
    -> Junction_10
Note: WorkGrpMapper_Output : Input
Junction_25
    -> Junction_26
Note: Log Output: FieldMapper
Junction_7
    -> Junction_8

Bookmark: 3. Create Maximo Service Request
  If the case is new, generate a new service request in Maximo, and notify an update containing the new service request identifier
Note: Populate a model SR XML / document for the Maximo / TRHFMESRCREATEES service / Jimmy add Worktype for WWW
Note: WorkAround for Lat/Long in Maximo / LAT / LONG commented out in NewSR_Templater. We run a CREATESR (HTTPCaller_New), followed by UPDATESR in Maximo (connection from ResponseParser to UpdateSRTemplater)
NewSR_Templater: XMLTemplater
    OUTPUT_XML_HEADER = Yes
    RESULT_ATTRIBUTE = CreateAsXML
    ROOT_QUERY_EXPR:
      <soapenv:Envelope xmlns:soapenv="http://schemas.xmlsoap.org/soap/envelope/" xmlns:max="http://www.ibm.com/maximo">
         <soapenv:Header/>
         <soapenv:Body>
          <max:CreateTRHFMESR>
               <max:TRHFMESRSet>
                    <max:SR>
                       <!--<max:TARGETSTART>2018-12-01T04:03:57-05:00</max:TARGETSTART>-->
                       <!--<max:TARGETFINISH>2018-12-01T04:03:57-05:00</max:TARGETFINISH>-->
                       <max:TARGETSTART>@DateTimeFormat(@DateTimeParse(@Value(MX_SCHEDSTART),%Y-%m-%d %H:%M:%S,repair),%Y-%m-%dT%T)</max:TARGETSTART>
                       <max:TARGETFINISH>@DateTimeFormat(@TimeZoneSet(@DateTimeParse(@Value(SR_QA.Total_Response_Time),%Y-%m-%dT%H:%M:%S%z),local),%Y-%m-%dT%T)</max:TARGETFINISH>
                       <!--<max:WORKTYPE>IV</max:WORKTYPE>-->
                       <max:CLASS>SR</max:CLASS>
                       <max:ORGID>TRH</max:ORGID>
                       <max:SITEID>WAMS</max:SITEID>
                       <max:TRHFMEREQUESTID>{fme:get-attribute("TRHFMEREQUESTID")}</max:TRHFMEREQUESTID>
                       <max:DESCRIPTION>{fme:get-attribute("DESCRIPTION")}</max:DESCRIPTION>
                       <max:DESCRIPTION_LONGDESCRIPTION>{fme:get-attribute("DESCRIPTION_LONGDESCRIPTION")}</max:DESCRIPTION_LONGDESCRIPTION>
                       <max:LOCATION>{fme:get-attribute("LOCATION")}</max:LOCATION>
                       <max:TRHCALLERADDRESS>{fme:get-attribute("TRHCALLERADDRESS")}</max:TRHCALLERADDRESS>
                       <max:TRHCELLNUMBER>{fme:get-attribute("TRHCELLNUMBER")}</max:TRHCELLNUMBER>
                       <max:TRHEMAIL>{fme:get-attribute("TRHEMAIL")}</max:TRHEMAIL>
                       <max:TRHFIRSTNAME>{fme:get-attribute("TRHFIRSTNAME")}</max:TRHFIRSTNAME>
                       <max:TRHLASTNAME>{fme:get-attribute("TRHLASTNAME")}</max:TRHLASTNAME>
                       <max:TRHPHONENUMBER>{fme:get-attribute("TRHPHONENUMBER")}</max:TRHPHONENUMBER>
                       <max:TRH_ASSETNUM>{fme:get-attribute("TRH_ASSETNUM")}</max:TRH_ASSETNUM>
                       <max:JPNUM>{fme:get-attribute("JPNUM")}</max:JPNUM>
                       <max:TRH_BLOCK>{fme:get-attribute("TRH_BLOCK")}</max:TRH_BLOCK>
                       <max:TRH_OWNERGROUP>{fme:get-attribute("TRH_OWNERGROUP")}</max:TRH_OWNERGROUP>
                       <max:OWNER>{fme:get-attribute("OWNER")}</max:OWNER>
                       <max:TRHCRMCASEID>{fme:get-attribute("TRHCRMCASEID")}</max:TRHCRMCASEID>
                       <max:TRHAMPRIORITY>{fme:get-attribute("TRHAMPRIORITY")}</max:TRHAMPRIORITY>
                       <max:TRHDIRECTIONS>{fme:get-attribute("TRHDIRECTIONS")}</max:TRHDIRECTIONS>
                       <max:TKSERVICEADDRESS>
                          <max:FORMATTEDADDRESS>{fme:get-attribute("TKSERVICEADDRESS.FORMATTEDADDRESS")}</max:FORMATTEDADDRESS>
                          <max:ADDRESSLINE2>{fme:get-attribute("TKSERVICEADDRESS.ADDRESSLINE2")}</max:ADDRESSLINE2>
                          <max:ADDRESSLINE3/>
                          <max:CITY>{fme:get-attribute("TKSERVICEADDRESS.CITY")}</max:CITY>
                          <!-- <max:COUNTRY>{fme:get-attribute("TKSERVICEADDRESS.COUNTRY")}</max:COUNTRY> -->
                          <max:DIRECTIONS>{fme:get-attribute("TKSERVICEADDRESS.DIRECTIONS")}</max:DIRECTIONS>
                          <max:LATITUDEY>{fme:get-attribute("TKSERVICEADDRESS.LATITUDEY")}</max:LATITUDEY>
                          <max:LONGITUDEX>{fme:get-attribute("TKSERVICEADDRESS.LONGITUDEX")}</max:LONGITUDEX>
                          <max:ORGID>TRH</max:ORGID>
                          <max:POSTALCODE>{fme:get-attribute("TKSERVICEADDRESS.POSTALCODE")}</max:POSTALCODE>
                          <max:STATEPROVINCE>ON</max:STATEPROVINCE>
                          <max:STREETADDRESS>{fme:get-attribute("TKSERVICEADDRESS.STREETADDRESS")}</max:STREETADDRESS>
                       </max:TKSERVICEADDRESS>
                    </max:SR>
            </max:TRHFMESRSet>
          </max:CreateTRHFMESR>
      </soapenv:Body>
      </soapenv:Envelope>
    VISIBLE_QUERY_VALIDATE = Yes
    -> XMLFormatter
Note: Remove NULL attributes / from XML document
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = Yes
    REPLACE_TABS_WITH_SPACES = no
    SCHEMALOC_CLEANUP = No
    TEXT_INDENT = no
    WHITESPACE_HANDLING = Preserve all whitespace
    XML_ATTR_TEXT = CreateAsXML
    XML_INPUT_TYPE = Attribute Specifying XML Text
    XML_OUTPUT_ATTR = CreateAsXML
    XML_OUTPUT_TYPE = Attribute
    PASSED -> HTTPCaller
    PASSED -> Junction_13
Note: POST XML document to / TRHFMESRCREATEES service
HTTPCaller
    AUTH_METHOD = Web Connection
    AUTH_NAMED_CONNECTION = Maximo
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(MaximoServiceUrl)/TRHFMESYS_TRHFMESRCREATEES
    TRANSFER_TIMEOUT_LENGTH = 90
    UPLOAD_BODY = @Value(CreateAsXML)
    UPLOAD_CONTENT_TYPE = text/xml
    UPLOAD_TYPE = Specify Upload Body
    USE_COOKIES = No
    VERIFY_SSL_CERTIFICATES = No
    -> AttributeKeeper
    <REJECTED> -> Junction_15
    <REJECTED> -> Terminator
Note: Keep the message response, / HTTP status code, and the / updates to return to SF.com
AttributeKeeper
    KEEP_ATTRS = _response_body,OWNER,TKSERVICEADDRESS.LATITUDEY,TRHFMEREQUESTID,TICKETID,TKSERVICEADDRESS.LONGITUDEX,_http_status_code
    -> ResponseParser
Note: Get the TICKETID and OWNER / assigned for the new SR in Maximo
ResponseParser: XMLFragmenter
    ATTRIBUTE_XML = _response_body
    EMBEDDED_EXPRESSIONS = SR
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = TICKETID TRHFMEREQUESTID STATUS OWNER TKSERVICEADDRESS.LATITUDEY TKSERVICEADDRESS.LONGITUDEX
    REJECT_FEATURES_WITH_NO_FRAGMENTS = YES
    XML_SOURCE_TYPE = Attribute with XML document
    FRAGMENTS -> Junction_27 [off]
    FRAGMENTS -> AttributeCreator_3
    <REJECTED> -> ResponseParser__Rejected_
AttributeCreator_3
    ATTR_TABLE:
      SET_TO MaximoID = @Value(TICKETID)
      SET_TO SFID = @Value(TRHFMEREQUESTID)
    -> MessageBuilder
Note: Build the JSON message / to update in canonical form
MessageBuilder
    OWNER = @Value(OWNER)
    STATUS = @Value(STATUS)
    TICKETID = @Value(TICKETID)
    TKSERVICEADDRESS.LATITUDEY = @Value(TKSERVICEADDRESS.LATITUDEY)
    TKSERVICEADDRESS.LONGITUDEX = @Value(TKSERVICEADDRESS.LONGITUDEX)
    TRHFMEREQUESTID = @Value(TRHFMEREQUESTID)
    -> FMEServerNotifier
    -> Junction_17
Note: Send update message / to notifier service
FMEServerNotifier
    BODY = @Value(UpdateSFJSON)
    SERVER_CONNECTION = $(SERVER_CONNECTION)
    TOPIC = SRUpdateFromMaximo
    -> SQLExecutor_2 [INITIATOR]
    <REJECTED> -> Junction_19
    <REJECTED> -> Terminator_3
Note: Update Queue message
SQLExecutor_2
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER ;
      UPDATE dbo.[fme_case_queue]
      SET [status] = 'ReturnId', [backend_id] = '@Value(MaximoID)', [job_id] = $(FME_JOB_ID)
      WHERE [salesforce_id] = '@Value(SFID)' AND [status] = 'InProgress';
    <REJECTED> -> Logger_2
Logger_2
    LOG_FEATURE = LOG_ONLY
    MAXCOORDS = 20
    MAXFEATS = 20
    MESSAGE = Error Updating fme_case_queue SQL
    SEVERITY = ERROR
    LOGGED -> Terminator_5
Terminator_5
    MESSAGE = Translation Terminated
Terminator_3
    MESSAGE:
      Maximo Id was not updated in Salesforce. You can run the following JSON manually through the SalesforceUpdate workspace:
      @Value(UpdateSFJSON)
Note: FMEServerNotifier_Rejected : Input
Junction_19
    -> Junction_20
Note: NotifierMessage_Log : Input
Junction_17
    -> Junction_18
Note: UpdateSRTemplater : Lat/Long / DISABLED
Junction_27
    -> Junction_28
ResponseParser__Rejected_: Logger
    LOG_FEATURE = LOG_RECORD
    MAXCOORDS = 20
    MAXFEATS = 20
    MESSAGE = Feature is:
    SEVERITY = INFO
Terminator
    MESSAGE = MaximoUpdateService could not post the message to Maximo.  Check connection and resubmit job.
Note: HTTPCaller_Rejected_ Log: Input
Junction_15
    -> Junction_16
Note: CreateSRXML_Log : Input
Junction_13
    -> Junction_14

Bookmark: Log Outputs
Note: FMEServerNotifier : Rejected
Junction_20
    -> FMEServerNotifier_Rejected
FMEServerNotifier_Rejected: Logger
    LOG_FEATURE = LOG_RECORD
    MAXCOORDS = 20
    MAXFEATS = 20
    MESSAGE = FMEServerNotifier Error is:
    SEVERITY = INFO
Note: MessageBuilder : Output
Junction_18
    -> NotifierMessage_Log
NotifierMessage_Log: Logger
    LOG_FEATURE = LOG_RECORD
    MAXCOORDS = 20
    MAXFEATS = 20
    MESSAGE = Message to Notifier Topic is:
    SEVERITY = INFO
Note: HTTPCaller : Rejected
Junction_16
    -> HTTPCaller_Rejected_Log
Note: XMLFormatter : Passed
Junction_14
    -> CreateSRXML_Log
CreateSRXML_Log: Logger
    LOG_FEATURE = LOG_RECORD
    MAXCOORDS = 20
    MAXFEATS = 20
    MESSAGE = XML for Maximo Create service is:
    SEVERITY = INFO
Note: HTTPCaller_Update : Output
Junction_24
    -> HTTPCaller_Success
HTTPCaller_Success: Logger
    LOG_FEATURE = LOG_RECORD
    MAXCOORDS = 20
    MAXFEATS = 20
    MESSAGE = Response from Maximo for POST is:
    SEVERITY = INFO
Junction_22
    -> HTTPCaller_Rejected_Log
HTTPCaller_Rejected_Log: Logger
    LOG_FEATURE = LOG_RECORD
    MAXCOORDS = 20
    MAXFEATS = 20
    MESSAGE = FAILED to create new SR
    SEVERITY = INFO
Note: AttributeRemover: Output
Junction_10
    -> StepTwo_Log
StepTwo_Log: Logger
    LOG_FEATURE = LOG_RECORD
    MAXCOORDS = 20
    MAXFEATS = 20
    MESSAGE = Step 2 Output is:
    SEVERITY = INFO
Note: WorkGrpMapper : Output
Junction_26
    -> WorkGrpMapper_Output
WorkGrpMapper_Output: Logger
    LOG_FEATURE = LOG_RECORD
    MAXCOORDS = 20
    MAXFEATS = 20
    MESSAGE = Maximo WorkGroup Mapper is:
    SEVERITY = INFO
Note: FieldMapper: Output
Junction_8
    -> FieldMapper_Log
FieldMapper_Log: Logger
    LOG_FEATURE = LOG_RECORD
    MAXCOORDS = 20
    MAXFEATS = 20
    MESSAGE = FieldMapper Output is:
    SEVERITY = INFO
Note: AttributeExposer: Output
Junction_4
    -> ReceivedSR_Log
ReceivedSR_Log: Logger
    LOG_FEATURE = LOG_RECORD
    MAXCOORDS = 20
    MAXFEATS = 20
    MESSAGE = Canonical Service Request Is:
    SEVERITY = INFO
Note: TopicFlattener: Output
Junction_2
    -> TopicFlattener_Log
TopicFlattener_Log: Logger
    LOG_FEATURE = LOG_RECORD
    MAXCOORDS = 20
    MAXFEATS = 20
    MESSAGE = Feature is:
    SEVERITY = INFO

Bookmark: 4. Update Maximo Service Request
  If the case has been previously created in Maximo as a service request, update the key information (contact, problem location, or status = close)
Note: ResponseParser : Lat / Long Update
Junction_28
    -> UpdateSRTemplater [ROOT]
IsClosed: Tester
    BOOL_OP = OR
    TEST_CLAUSE = TEST STATUS = CLOSED
    PASSED -> AttributeCreator_2
    FAILED -> UpdateSRTemplater [ROOT]
Note: Add reason to case closed / request as worklog entry
AttributeCreator_2
    ATTR_TABLE = SET_TO StatusChangeRequestedMsg = <b>ARH Advisor requests that this case be closed</b></br>
    -> UpdateSRTemplater [ROOT]
Note: Populate a model SR XML / document for Maximo / TRHFMESRUPDATEES service
UpdateSRTemplater: XMLTemplater
    OUTPUT_XML_HEADER = Yes
    RESULT_ATTRIBUTE = UpdateSRXML
    ROOT_QUERY_EXPR:
      <soapenv:Envelope xmlns:soapenv="http://schemas.xmlsoap.org/soap/envelope/" xmlns:max="http://www.ibm.com/maximo">
         <soapenv:Header/>
         <soapenv:Body>
      	<max:UpdateTRHFMESR>
        	   <max:TRHFMESRSet>
        	   <max:SR action="Change">
      	      <max:CLASS>SR</max:CLASS>
      	      <max:TICKETID>{fme:get-attribute("TICKETID")}</max:TICKETID>
      	      <max:ORGID>TRH</max:ORGID>
      	      <max:SITEID>WAMS</max:SITEID>
                       <max:TRHFMEREQUESTID>{fme:get-attribute("TRHFMEREQUESTID")}</max:TRHFMEREQUESTID>
                       <max:TRHCRMCASEID>{fme:get-attribute("TRHCRMCASEID")}</max:TRHCRMCASEID>
                       <max:DESCRIPTION>{fme:get-attribute("DESCRIPTION")}</max:DESCRIPTION>
                       <max:DESCRIPTION_LONGDESCRIPTION>{fme:get-attribute("DESCRIPTION_LONGDESCRIPTION")}</max:DESCRIPTION_LONGDESCRIPTION>
                       <max:STATUS>{fme:get-attribute("STATUS")}</max:STATUS>
                       <max:LOCATION>{fme:get-attribute("LOCATION")}</max:LOCATION>
                       <max:TRHCALLERADDRESS>{fme:get-attribute("TRHCALLERADDRESS")}</max:TRHCALLERADDRESS>
                       <max:TRHCELLNUMBER>{fme:get-attribute("TRHCELLNUMBER")}</max:TRHCELLNUMBER>
                       <max:TRHEMAIL>{fme:get-attribute("TRHEMAIL")}</max:TRHEMAIL>
                       <max:TRHFIRSTNAME>{fme:get-attribute("TRHFIRSTNAME")}</max:TRHFIRSTNAME>
                       <max:TRHLASTNAME>{fme:get-attribute("TRHLASTNAME")}</max:TRHLASTNAME>
                       <max:TRHPHONENUMBER>{fme:get-attribute("TRHPHONENUMBER")}</max:TRHPHONENUMBER>
                       <max:TRH_ASSETNUM>{fme:get-attribute("TRH_ASSETNUM")}</max:TRH_ASSETNUM>
                       <max:LOCATION>{fme:get-attribute("LOCATION")}</max:LOCATION>
                       <max:TRH_BLOCK>{fme:get-attribute("TRH_BLOCK")}</max:TRH_BLOCK>
                       <max:TRH_OWNERGROUP>{fme:get-attribute("TRH_OWNERGROUP")}</max:TRH_OWNERGROUP>
                       <max:TRHDIRECTIONS>{fme:get-attribute("TRHDIRECTIONS")}</max:TRHDIRECTIONS>
                       <max:TKSERVICEADDRESS>
                          <max:FORMATTEDADDRESS>@Trim({fme:get-attribute("TKSERVICEADDRESS.FORMATTEDADDRESS")})</max:FORMATTEDADDRESS>
                          <max:ADDRESSLINE2>{fme:get-attribute("TKSERVICEADDRESS.ADDRESSLINE2")}</max:ADDRESSLINE2>
                          <max:ADDRESSLINE3/>
                          <max:CITY>{fme:get-attribute("TKSERVICEADDRESS.CITY")}</max:CITY>
                          <!-- <max:COUNTRY>{fme:get-attribute("TKSERVICEADDRESS.COUNTRY")}</max:COUNTRY> -->
                          <max:DIRECTIONS>{fme:get-attribute("TKSERVICEADDRESS.DIRECTIONS")}</max:DIRECTIONS>
                          <max:LATITUDEY>{fme:get-attribute("TKSERVICEADDRESS.LATITUDEY")}</max:LATITUDEY>
                          <max:LONGITUDEX>{fme:get-attribute("TKSERVICEADDRESS.LONGITUDEX")}</max:LONGITUDEX>
                          <max:ORGID>TRH</max:ORGID>
                          <max:POSTALCODE>{fme:get-attribute("TKSERVICEADDRESS.POSTALCODE")}</max:POSTALCODE>
                          <max:STATEPROVINCE>ON</max:STATEPROVINCE>
                          <max:STREETADDRESS>{fme:get-attribute("TKSERVICEADDRESS.STREETADDRESS")}</max:STREETADDRESS>
                       </max:TKSERVICEADDRESS>
                       <max:WORKLOG>
                          <max:DESCRIPTION>{fme:get-attribute("CloseReason")}</max:DESCRIPTION>
                          <max:DESCRIPTION_LONGDESCRIPTION>{fme:get-attribute("StatusChangeRequestedMsg")}{fme:get-attribute("ClosedComments")}</max:DESCRIPTION_LONGDESCRIPTION>
                       </max:WORKLOG>
            </max:SR>
      	  </max:TRHFMESRSet>
      	</max:UpdateTRHFMESR>
      </soapenv:Body>
      </soapenv:Envelope>
    VISIBLE_QUERY_VALIDATE = Yes
    -> XMLFormatter_2
Note: Remove NULL attributes / from XML document
XMLFormatter_2
    COLLAPSE_EMPTY_ELEMENT = Yes
    FORMATTING_CHOICE = Pretty-Print XML
    INDENT_SIZE = 3
    LIST_NAME = _xml_error
    NAMESPACE_CLEANUP = No
    OUTPUT_ENCODING = utf-8
    REMOVE_ALL_COMMENT = Yes
    REMOVE_EMPTY_ELEMENT = Yes
    REPLACE_TABS_WITH_SPACES = yes
    SCHEMALOC_CLEANUP = No
    TEXT_INDENT = yes
    WHITESPACE_HANDLING = Preserve all whitespace
    XML_ATTR_TEXT = UpdateSRXML
    XML_INPUT_TYPE = Attribute Specifying XML Text
    XML_OUTPUT_ATTR = UpdateSRXML
    XML_OUTPUT_TYPE = Attribute
    PASSED -> HTTPCaller_Update
Note: POST XML document to / TRHFMESRUPDATEES service
HTTPCaller_Update
    AUTH_METHOD = Web Connection
    AUTH_NAMED_CONNECTION = Maximo
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(MaximoServiceUrl)/TRHFMESYS_TRHFMESRUPDATEES
    TRANSFER_TIMEOUT_LENGTH = 90
    UPLOAD_BODY = @Value(UpdateSRXML)
    UPLOAD_CONTENT_TYPE = text/xml
    UPLOAD_TYPE = Specify Upload Body
    USE_COOKIES = No
    VERIFY_SSL_CERTIFICATES = No
    -> SQLExecutor [INITIATOR]
    <REJECTED> -> Junction_21
    <REJECTED> -> Terminator_2
Note: Delete row from queue
SQLExecutor
    COMBINE_ATTRS = Result Attributes Only
    COMBINE_GEOM = Initiator Geometry Only
    DATASET = TWV-SQL3_QueueDB
    EXPOSED_ATTRIBUTE_LIST = SalesforceId
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER ;
      DELETE FROM dbo.[fme_case_queue]
      WHERE [salesforce_id] = '@Value(TRHFMEREQUESTID)' AND [status] = 'InProgress';
    INITIATOR -> Junction_23
    <REJECTED> -> Logger_3
Note: HTTPCaller_Success : Input
Junction_23
    -> Junction_24
Logger_3
    LOG_FEATURE = LOG_ONLY
    MAXCOORDS = 20
    MAXFEATS = 20
    MESSAGE = Error DELETING row from fme_case_queue SQL
    SEVERITY = ERROR
    LOGGED -> Terminator_6
Terminator_2
    MESSAGE = MaximoUpdateService could not post the message to Maximo.  Check connection and resubmit job.
Note: HTTPCaller_Rejected_Log: Input
Junction_21
    -> Junction_22

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
Input Ports
    Input
Accepts any feature.
    Output Ports
    Output
Ouputs the original feature with an added attribute containing the JSON object.
    Parameters
    Attributes to Pack
    Specific attributes to pack. Chosing any attributes will disable the filter (described below).
    Filter Prefix
All attributes with this prefix will be added to the packed attribute. Leaving this value blank will pack all the attributes.
    Packed Attribute Name
The name of the new attribute containing the packed values

Parameters:
- FILTER =   # Filter Prefix (blank for all attributes)
- PACKED = _packed   # Packed Attribute Name
- ATTRS =   # " " Attributes to Pack

Input (input)
    -> ParameterFetcher
Note: Get filter value
ParameterFetcher
    ATTR_LIST = AttributeJSONPacker_FILTER {$(FILTER)} AttributeJSONPacker_PACKED {$(PACKED)} AttributeJSONPacker_ATTRS {$(ATTRS)}
    -> PythonCaller
PythonCaller
    NEW_ATTRIBUTES = $(PACKED)
    PYTHONSOURCE:
      from __future__ import absolute_import, division, print_function, unicode_literals

      import fmeobjects
      import binascii
      import json
      import six

      # This class will create a packed list of format
      # attributes suitable for use with @SupplyAttributes()

      def packIgdsAtts(feature):
         # get a list of attribute names
         attlist = feature.getAllAttributeNames()
         attlist = map(six.text_type, attlist)

         # get attributes to pack
         pack_attrs = feature.getAttribute('AttributeJSONPacker_ATTRS').replace('"', '').strip().split(',')

         # get filter value
         filter = feature.getAttribute('AttributeJSONPacker_FILTER')


         # get packed attribute name
         packedAtt = feature.getAttribute('AttributeJSONPacker_PACKED')

         addedAttrs = {
            'AttributeJSONPacker_ATTRS',
            'AttributeJSONPacker_FILTER',
            'AttributeJSONPacker_PACKED',
         }

         # disable filter if packed attribute chosen
         if pack_attrs[0] != "":
             filter = False

         # create dict for packed attributes
         packed = {}

         # loop through attribute names
         for att in attlist:
             if ((filter and filter in att) or att in pack_attrs) and att not in addedAttrs:
                 att_value = feature.getAttribute(att)
                 float_val, int_val = None, None
                 try:
                     float_val = float(att_value)
                     int_val = int(att_value)
                     if int_val == float_val:
                         att_value = int_val
                     else:
                         att_value = float_val
                 except ValueError as e:
                     if int_val is not None:
                         att_value = int_val
                     if float_val is not None:
                         att_value = float_val

                 # convert binary attributes to hex for storage
                 if type(att_value) == bytearray:
                     att_value = "0x" + binascii.hexlify(att_value)
                 # append attribute value
                 packed[att] = att_value

         #add packed attributes in JSON format
         feature.setAttribute(packedAtt,json.dumps(packed,separators=(',', ':'), ensure_ascii=False))
    PYTHONSYMBOL = packIgdsAtts
    -> Output (output)
Output (output)

FME custom transformer MessageBuilder

Parameters:
- OWNER = @Value(OWNER)
- STATUS = @Value(STATUS)
- TICKETID = @Value(TICKETID)
- TRHFMEREQUESTID = @Value(TRHFMEREQUESTID)
- TKSERVICEADDRESS.LATITUDEY = @Value(TKSERVICEADDRESS.LATITUDEY)
- TKSERVICEADDRESS.LONGITUDEX = @Value(TKSERVICEADDRESS.LONGITUDEX)

Input (input)
    -> AttributeRenamer
Note: Schema Mapping of Maximo / to Canonical atttributes
AttributeRenamer
    ATTR_TABLE:
      RENAME_SET_DEFAULT OWNER > AssignedTo
      RENAME_SET_DEFAULT TICKETID > Target_Request_Id
      RENAME_SET_DEFAULT TRHFMEREQUESTID > Source_Request_Id
      RENAME_SET_DEFAULT STATUS > Status
      RENAME_SET_DEFAULT TKSERVICEADDRESS.LATITUDEY > Latitude
      RENAME_SET_DEFAULT TKSERVICEADDRESS.LONGITUDEX > Longitude
    -> AttributeJSONPacker
AttributeJSONPacker
    ATTRS = Longitude,Target_Request_Id,Source_Request_Id,AssignedTo,Latitude
    PACKED = UpdateSFJSON
    -> AttributeExposer_5
Note: Show the resultant JSON message
AttributeExposer_5
    ATTR_LIST = UpdateSFJSON
    -> Output (output)
Output (output)
