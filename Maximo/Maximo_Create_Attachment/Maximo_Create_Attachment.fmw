FME workspace Maximo_Create_Attachment.fmw

Parameters:
- SourceDataset_SF_Attachment = C:\Users\fiona.hatfield\Documents\FME\Workspaces\DownloadedFromUAT\Maximo\SampleInputCanonical_attachment.json   # Source Text File(s)
- MaximoServiceUrl = http://wamsif.richmondhill.ca/meaweb/services/   # Maximo Server URL
- DOCLINKURL = http://pwv-wamsadmin.richmondhill.local/DEFAULT/

Readers:
- TEXTLINE_1: TEXTLINE from $(SourceDataset_SF_Attachment)

Note: Update queue with JobId, Process_Date
SQLExecutor_2
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      UPDATE dbo.[fme_attachment_queue]
      SET [job_id] = $(FME_JOB_ID), [process_date] = CURRENT_TIMESTAMP, [status] = 'InProgress'
      WHERE [attachment_id] = '@Value(Attachment_Id)' AND [status] = 'Pending'
    INITIATOR -> AttributeCreator
    <REJECTED> -> Terminator
Terminator
    MESSAGE = Translation Terminated

Bookmark: Read SF Attachment Data
text_line (reader TEXTLINE_1)
    attributes: text_line_data buffer
    -> JSONTemplater [ROOT]
Note: Read SF Attachment Data
JSONTemplater
    RESULT_ATTRIBUTE = _result
    ROOT_QUERY_EXPR = @Value(text_line_data)
    VISIBLE_QUERY_VALIDATE = Yes
    -> JSONFlattener
JSONFlattener
    ERROR_LIST_ATTR = _json_error
    JSON_DOCUMENT = @Value(_result)
    NEW_ATTRIBUTES = Target_System_Id Source_System_Id AttachmentName filename Attachment_Id
    READ_FROM_FILE = NO
    RECURSIVE = Yes
    -> JSONFlattener_Output
    -> SQLExecutor_2 [INITIATOR]
JSONFlattener_Output: Logger
    LOG_FEATURE = LOG_RECORD
    MAXCOORDS = 20
    MAXFEATS = 20
    MESSAGE = Feature is: Input Canonical Data
    SEVERITY = INFO

Bookmark: Extract File Path
AttributeCreator
    ATTR_TABLE = SET_TO URLName = $(DOCLINKURL)@Value(filename)
    -> XMLTemplater_2 [ROOT]

Bookmark: Add MAximo Attachment
Note: Call UpdateTRHFMESR
XMLTemplater_2
    OUTPUT_XML_HEADER = Yes
    RESULT_ATTRIBUTE = Insert_Attachment
    ROOT_QUERY_EXPR:
      <soapenv:Envelope xmlns:soapenv="http://schemas.xmlsoap.org/soap/envelope/" xmlns:max="http://www.ibm.com/maximo">
         <soapenv:Header/>
         <soapenv:Body>
      	<max:UpdateTRHFMESR>
        	   <max:TRHFMESRSet>
        	   <max:SR action="Change">

      	      <max:CLASS>SR</max:CLASS>
      	      <max:TICKETID>{fme:get-attribute("Target_System_Id")}</max:TICKETID>
      	      <max:ORGID>TRH</max:ORGID>
      	      <max:SITEID>WAMS</max:SITEID>
      	      <max:TRHFMEREQUESTID>{fme:get-attribute("Source_System_Id")}</max:TRHFMEREQUESTID>

                  <max:DOCLINKS>
                      <max:DESCRIPTION>{fme:get-attribute("AttachmentName")}</max:DESCRIPTION>
                      <max:DOCTYPE>Attachments</max:DOCTYPE>
                      <max:URLNAME>{fme:get-attribute("URLName")}</max:URLNAME>
                      <max:URLTYPE>FILE</max:URLTYPE>
                  </max:DOCLINKS>

                  </max:SR>
      	  </max:TRHFMESRSet>
      	</max:UpdateTRHFMESR>
      </soapenv:Body>
      </soapenv:Envelope>
    VISIBLE_QUERY_VALIDATE = Yes
    -> XMLFormatter_2
XMLFormatter_2
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = Yes
    REPLACE_TABS_WITH_SPACES = no
    SCHEMALOC_CLEANUP = No
    TEXT_INDENT = no
    WHITESPACE_HANDLING = Preserve all whitespace
    XML_ATTR_TEXT = Insert_Attachment
    XML_INPUT_TYPE = Attribute Specifying XML Text
    XML_OUTPUT_ATTR = UpdateSRXML
    XML_OUTPUT_TYPE = Attribute
    PASSED -> HTTPCaller_3
HTTPCaller_3
    AUTH_METHOD = Web Connection
    AUTH_NAMED_CONNECTION = Maximo
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(MaximoServiceUrl)/TRHFMESYS_TRHFMESRUPDATEES
    TRANSFER_TIMEOUT_LENGTH = 90
    UPLOAD_BODY = @Value(UpdateSRXML)
    UPLOAD_CONTENT_TYPE = text/xml
    UPLOAD_TYPE = Specify Upload Body
    USE_COOKIES = No
    VERIFY_SSL_CERTIFICATES = No
    -> HTTPCaller_3_Output_2
HTTPCaller_3_Output_2: Logger
    LOG_FEATURE = LOG_RECORD
    MAXCOORDS = 20
    MAXFEATS = 20
    MESSAGE = Feature is: Output Canonical Data
    SEVERITY = INFO
    LOGGED -> SQLExecutor [INITIATOR]
Note: Delete from queue
SQLExecutor
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      DELETE FROM dbo.[fme_attachment_queue]
      WHERE [attachment_id] = '@Value(Attachment_Id)' AND [status] = 'InProgress'
    INITIATOR -> Logger
    <REJECTED> -> Terminator_2
Logger
    LOG_FEATURE = LOG_ONLY
    MAXCOORDS = 20
    MAXFEATS = 20
    MESSAGE = I should have deleted the record
    SEVERITY = INFO
Terminator_2
    MESSAGE = Translation Terminated
