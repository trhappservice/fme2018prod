FME workspace MaximoQueryService.fmw

Parameters:
- RetrieveFromTimestamp = 2018-10-17T19:00:00-4:00   # Retrieve records starting at the indicated ISO timestamp
- IsUserTimestamp = NO   # Select whether to enter your own timestamp or use system-generated timestamp
- MaximoServiceUrl = http://wamsif.richmondhill.ca/meaweb/services   # Maximo Server URL
- TimeStampFile = $(FME_SHAREDRESOURCE_DATA)\Salesforce\LastMaximoTimestamp.ffs   # FFS File containing the attribute for last timestamp read
- DestDataset_FFS = $(FME_SHAREDRESOURCE_DATA)\Salesforce\LastMaximoTimestamp.ffs   # Destination FME Feature Store (FFS) File
- SchemaMapper = $(FME_SHAREDRESOURCE_DATA)\Salesforce\CanonicalMapping.xlsx   # "" Path to the Maximo-Canonical-Salesforce schema mapping file
- MaxIntAdmin = MXINTADM   # Maximo Integration User Name
- SERVER_CONNECTION = FME Server   # "FME Server" Connection

Writers:
- FFS_1: FFS to $(DestDataset_FFS)

SQLExecutor
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER |
      IF NOT EXISTS (SELECT *
              FROM dbo.[fme_case_queue]
              WHERE [salesforce_id] = '@Value(Source_Request_Id)'
              AND [status] = 'ReturnToSF')
          BEGIN
              INSERT INTO dbo.[fme_case_queue] ([salesforce_id], [status], [backend_id], [backend_system], [canonical], [date_added], [job_id])
              VALUES ('@Value(Source_Request_Id)', 'ReturnToSF', '@Value(Target_Request_Id)', 'MAXIMO', '@Value(_packed)', CURRENT_TIMESTAMP, $(FME_JOB_ID))
          END
      ELSE
          IF EXISTS (SELECT *
              FROM dbo.[fme_case_queue]
              WHERE [salesforce_id] = '@Value(Source_Request_Id)'
              AND [status] = 'ReturnToSF')
          BEGIN
              UPDATE dbo.[fme_case_queue] SET [backend_id] = '@Value(Target_Request_Id)', [backend_system] = 'MAXIMO', [canonical] = '@Value(_packed)', [date_added] = CURRENT_TIMESTAMP
              WHERE [salesforce_id] = '@Value(Source_Request_Id)' AND [status] = 'ReturnToSF'
          END;
      SELECT * FROM dbo.[fme_case_queue] WHERE [salesforce_id] = '@Value(Source_Request_Id)' AND [status] = 'ReturnToSF';
      |
    INITIATOR -> JSONFormatter
    <REJECTED> -> Terminator_3
Terminator_3
    MESSAGE = "SQLExecutor FAILED - "

Bookmark: 1. Query Maximo Service Requests
  Poll the Maximo query service on a regular basis to retrieve all records updated with the last x minutes
Creator
    GEOMTYPE = Geometry Object
    NUM = 1
    CREATED -> TimestampTester
Note: Check if user has entered / a timestamp to run
TimestampTester: Tester
    BOOL_OP = AND
    TEST_CLAUSE:
      TEST $(RetrieveFromTimestamp) ATTRIBUTE_HAS_VALUE ""
      TEST $(IsUserTimestamp) = Yes
    PASSED -> ParameterFetcher
    FAILED -> FeatureReader [INITIATOR]
Note: Retrieve the user- / provided timestamp
ParameterFetcher
    ATTR_LIST = timestamp $(RetrieveFromTimestamp)
    -> SOAPFormatter
Note: Read the timestamp for / the last successful run
FeatureReader
    ATTRIBUTES = Timestamp,timestamp
    ATTRS_TO_EXPOSE = fme_feature_type timestamp
    ATTR_ACCUM_MODE = Only Use Result
    COMBINE_GEOM = Use Result
    DATASET = $(TimeStampFile)
    FEATURETYPES = Timestamp
    FFS_USE_SEARCH_ENVELOPE = NO
    FORMAT = FFS
    INTERACT = <No Spatial Filter>
    OUTPUT_FEATURES_DISPLAY = Data Features
    SELECTED_PORTS = Timestamp
    Timestamp -> SOAPFormatter
    <REJECTED> -> AttributeCreator_3
Note: Build the query to Maximo that retrieves / Work Order updates since the last query
SOAPFormatter: AttributeCreator
    ATTR_TABLE:
      SET_TO xmlToQuery = <soapenv:Envelope xmlns:soapenv="http://schemas.xmlsoap.org/soap/envelope/" xmlns:max="http://www.ibm.com/maximo">
          <soapenv:Header/>
           <soapenv:Body>
        	<max:QueryTRHFMESR xmlns:max="http://www.ibm.com/maximo" creationDateTime="2008-09-28T21:49:45" baseLanguage="EN" uniqueResult="0" rsStart="0">
          	  <max:TRHFMESRQuery>
            	  	<max:WHERE>TRHFMEREQUESTID is not null AND CHANGEDATE > TO_TIMESTAMP_TZ('@Value(timestamp)','YYYY-MM-DD"T"hh24:mi:ss.FFTZH:TZM')</max:WHERE>
        	  </max:TRHFMESRQuery>
        	</max:QueryTRHFMESR>
        	</soapenv:Body>
        </soapenv:Envelope>
    -> HTTPCaller44
Note: Call the Maximo web service / to retrieve records that match / the query
HTTPCaller44
    AUTH_METHOD = Web Connection
    AUTH_NAMED_CONNECTION = Maximo
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(MaximoServiceUrl)/TRHFMESYS_TRHFMESRQUERYES
    TRANSFER_TIMEOUT_LENGTH = 90
    UPLOAD_BODY = @Value(xmlToQuery)
    UPLOAD_CONTENT_TYPE = text/xml
    UPLOAD_TYPE = Specify Upload Body
    USE_COOKIES = No
    VERIFY_SSL_CERTIFICATES = No
    -> XMLFragmenter
    -> MaximoLogger
    <REJECTED> -> HTTPCaller__Rejected_
Note: Extract the message components for: / - Service Request (SR) / - Comments (WORKLOG) / - Communications (COMLOG) / - Attachments (DOCLINKS) / - Status Memos (TKSTATUS)
XMLFragmenter
    ATTRIBUTE_XML = _response_body
    EMBEDDED_EXPRESSIONS = SR WORKLOG COMLOG DOCLINKS TKSTATUS
    FEATURE_TYPES_FORMAT_NAME = XML
    FLATTEN_OPTIONS:
      <structure
      separator="."
      open-list-brace="{"
      close-list-brace="}"
      map-empty-elements="yes"
      matched-prefix="yes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    MERGE_ATTRS = Yes
    NEW_ATTRIBUTES = CHANGEDATE STATUSDATE TRHFMEREQUESTID TICKETID
    REJECT_FEATURES_WITH_NO_FRAGMENTS = YES
    XML_SOURCE_TYPE = Attribute with XML document
    FRAGMENTS -> BulkAttributeRenamer
    <REJECTED> -> XMLFragmenter_Fragments
Note: SR messages are prefixed / with 'SR.', remove prefix
BulkAttributeRenamer
    ATTRCHOICE = All Attributes
    CASE_DISP = YES
    MODE_CHOICE = RENAME
    PATTERN_ACTION_DISP = REMOVEPREFIX
    REPLACE_STR = SR.
    -> AttributeExposer_4
Note: Expose the list of / Maximo attributes
AttributeExposer_4
    ATTR_LIST = COMLOG.BCC,COMLOG.CC,COMLOG.COMLOGID,COMLOG.CREATEDATE,COMLOG.CREATEBY,COMLOG.INBOUND,COMLOG.MESSAGE,COMLOG.MODIFYDATE,COMLOG.MODIFYBY,COMLOG.REPLYTO,COMLOG.SENDFROM,COMLOG.SENDTO,COMLOG.SUBJECT,DESCRIPTION,DESCRIPTION_LONGDESCRIPTION,DOCLINKS.DESCRIPTION,DOCLINKS.DOCINFOID,DOCLINKS.DOCTYPE,DOCLINKS.OWNERID,DOCLINKS.OWNERTABLE,DOCLINKS.URLNAME,DOCLINKS.URLTYPE,GLOBALTICKETID,LOCATION,NP_STATUSMEMO,OWNER,STATUS,TICKETID,TKSERVICEADDRESS.ADDRESSLINE2,TKSERVICEADDRESS.CITY,TKSERVICEADDRESS.COUNTRY,TKSERVICEADDRESS.DIRECTIONS,TKSERVICEADDRESS.LATITUDEY,TKSERVICEADDRESS.LONGITUDEX,TKSERVICEADDRESS.POSTALCODE,TKSERVICEADDRESS.STATEPROVINCE,TKSERVICEADDRESS.STREETADDRESS,TKSTATUS.CHANGEDATE,TKSTATUS.MEMO,TKSTATUS.STATUS,TKSTATUS{}.CHANGEDATE,TKSTATUS{}.MEMO,TKSTATUS{}.STATUS,TRHAMPRIORITY,TRHCALLERADDRESS,TRHCELLNUMBER,TRHCRMCASEID,TRHEMAIL,TRHFIRSTNAME,TRHFMEREQUESTID,TRHLASTNAME,TRHPHONENUMBER,TRH_ASSETNUM,TRH_BLOCK,TRH_OWNERGROUP,WORKLOG.CREATEBY,WORKLOG.CREATEDATE,WORKLOG.DESCRIPTION,WORKLOG.DESCRIPTION_LONGDESCRIPTION,WORKLOG.LOGTYPE,WORKLOG.MODIFYBY,WORKLOG.MODIFYDATE,WORKLOG.WORKLOGID,fme_feature_type
    -> ListSearcher
ListSearcher
    ATTR_VALUE = @Value(STATUS)
    INDEX_ATTR = _list_index
    LIST_ATTR = TKSTATUS{}.STATUS
    SEARCH_TYPE = First exact match
    FOUND -> ListIndexer
    NOT_FOUND -> TestFilter
ListIndexer
    INDEX = @Value(_list_index)
    LIST_ATTR = TKSTATUS{}
    PREFIX = TKSTATUS.
    -> TestFilter
Note: Split based upon message type
TestFilter
    DEFAULT_VALUE = <UNFILTERED>
    TEST_LIST:
      BOOL_OP,AND,COMPOSITE_TEST,<Unused>,TEST_CLAUSE,"TEST @Value(xml_matched_element) = TKSTATUS
      TEST @Value(TKSTATUS.MEMO) ATTRIBUTE_HAS_VALUE """"",TKSTATUS,BOOL_OP,AND,COMPOSITE_TEST,<Unused>,TEST_CLAUSE,"TEST @Value(xml_matched_element) = WORKLOG
      TEST @Value(WORKLOG.MODIFYBY) != $(MaxIntAdmin)",WORKLOG,BOOL_OP,AND,COMPOSITE_TEST,<Unused>,TEST_CLAUSE,"TEST @Value(xml_matched_element) = COMLOG
      TEST @Value(COMLOG.MESSAGE) ATTRIBUTE_HAS_VALUE """"",COMLOG,BOOL_OP,COMPOSITE,COMPOSITE_TEST,"""1 AND (2 OR 3 OR 4)""",TEST_CLAUSE,"TEST @Value(xml_matched_element) = DOCLINKS
      TEST @UpperCase(@Value(DOCLINKS.DESCRIPTION)) CONTAINS JPG
      TEST @UpperCase(@Value(DOCLINKS.DESCRIPTION)) CONTAINS GIF
      TEST @UpperCase(@Value(DOCLINKS.DESCRIPTION)) CONTAINS PNG",DOCLINKS,BOOL_OP,OR,COMPOSITE_TEST,<Unused>,TEST_CLAUSE,"TEST @Value(xml_matched_element) = SR",SR
    TKSTATUS -> StatusKeeper
    WORKLOG -> WorklogKeeper
    COMLOG -> ComLogKeeper
    DOCLINKS -> DocLinksKeeper
    SR -> SRKeeper
    <UNFILTERED> -> IgnoredMessageLogger
Note: Trim the attributes down to / only those that are applicable / for the message type
StatusKeeper: AttributeKeeper
    KEEP_ATTRS = timestamp,TRHFMEREQUESTID,fme_feature_type,TKSTATUS.MEMO,xml_id,TKSTATUS.STATUS,xml_parent_id,xml_matched_element,TKSTATUS.CHANGEDATE
    -> AttributeRenamer
WorklogKeeper: AttributeKeeper
    KEEP_ATTRS = timestamp,TRHFMEREQUESTID,fme_feature_type,WORKLOG.CREATEDATE,WORKLOG.MODIFYDATE,xml_id,WORKLOG.LOGTYPE,WORKLOG.WORKLOGID,WORKLOG.DESCRIPTION_LONGDESCRIPTION,WORKLOG.CREATEBY,xml_parent_id,xml_matched_element,WORKLOG.DESCRIPTION,WORKLOG.MODIFYBY
    -> AttributeRenamer
ComLogKeeper: AttributeKeeper
    KEEP_ATTRS = COMLOG.REPLYTO,timestamp,xml_id,xml_matched_element,fme_feature_type,COMLOG.CREATEDATE,COMLOG.MESSAGE,COMLOG.INBOUND,COMLOG.CC,COMLOG.SENDTO,COMLOG.MODIFYDATE,COMLOG.SUBJECT,TRHFMEREQUESTID,xml_parent_id,COMLOG.MODIFYBY,COMLOG.COMLOGID,COMLOG.CREATEBY,COMLOG.SENDFROM,COMLOG.BCC
    -> AttributeRenamer
Note: Promote the MODIFYDATE / to CHANGEDATE and MODIFYBY / as standard attribute
AttributeRenamer
    ATTR_TABLE:
      RENAME_SET_DEFAULT TKSTATUS.CHANGEDATE > CHANGEDATE
      RENAME_SET_DEFAULT COMLOG.MODIFYDATE > CHANGEDATE
      RENAME_SET_DEFAULT WORKLOG.MODIFYDATE > CHANGEDATE
      RENAME_SET_DEFAULT COMLOG.MODIFYBY > MODIFYBY
      RENAME_SET_DEFAULT WORKLOG.MODIFYBY > MODIFYBY
    -> FeatureMerger [REQUESTOR]
DocLinksKeeper: AttributeKeeper
    KEEP_ATTRS = DOCLINKS.DOCINFOID,timestamp,DOCLINKS.DESCRIPTION,TRHFMEREQUESTID,fme_feature_type,DOCLINKS.OWNERTABLE,DOCLINKS.OWNERID,DOCLINKS.DOCTYPE,xml_id,xml_parent_id,DOCLINKS.URLNAME,xml_matched_element,DOCLINKS.URLTYPE
    -> FeatureMerger [REQUESTOR]
SRKeeper: AttributeKeeper
    KEEP_ATTRS = TKSERVICEADDRESS.POSTALCODE,TRHCRMCASEID,TKSERVICEADDRESS.LONGITUDEX,CHANGEDATE,TKSERVICEADDRESS.ADDRESSLINE2,TKSERVICEADDRESS.LATITUDEY,TKSTATUS.MEMO,timestamp,LOCATION,OWNER,TRHFMEREQUESTID,TRH_ASSETNUM,xml_matched_element,TICKETID,TKSERVICEADDRESS.STATEPROVINCE,TRHEMAIL,fme_feature_type,STATUSDATE,TKSERVICEADDRESS.STREETADDRESS,TRHCALLERADDRESS,TKSERVICEADDRESS.CITY,TRHLASTNAME,GLOBALTICKETID,STATUS,DESCRIPTION_LONGDESCRIPTION,TKSERVICEADDRESS.DIRECTIONS,TRH_OWNERGROUP,xml_id,DESCRIPTION,TKSERVICEADDRESS.COUNTRY,NP_STATUSMEMO,xml_parent_id,TRHFIRSTNAME,TRHAMPRIORITY,TRHPHONENUMBER,TRHCELLNUMBER,TRH_BLOCK
    -> FeatureMerger [SUPPLIER]
Note: Merge the service request infromation with log / attachment / status information to ensure that log entries are linked to the TICKETID / Case ID. Remove extraneouse attributes for each message type.
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(xml_parent_id) @Value(xml_id) AUTO
    MERGE_TYPE = Attributes Only
    PROCESS_DUPS = Yes
    REJECT_NULL_MISSING_KEYS = No
    SUPPLIERS_FIRST = No
    MERGED -> AttributeRemover
    USED_SUPPLIER -> AttributeRemover_2
    UNUSED_SUPPLIER -> AttributeRemover_2
AttributeRemover
    REMOVE_ATTRS = TKSTATUS.CHANGEDATE,TRH_OWNERGROUP,TRH_BLOCK,TKSERVICEADDRESS.CITY,TKSERVICEADDRESS.POSTALCODE,TRHLASTNAME,DESCRIPTION_LONGDESCRIPTION,DESCRIPTION,TRHPHONENUMBER,TRH_ASSETNUM,STATUSDATE,TRHEMAIL,OWNER,TRHCELLNUMBER,NP_STATUSMEMO,TRHCRMCASEID,xml_id,STATUS,TRHCALLERADDRESS,TRHFIRSTNAME,TKSERVICEADDRESS.LONGITUDEX,TKSERVICEADDRESS.COUNTRY,xml_parent_id,GLOBALTICKETID,TKSERVICEADDRESS.DIRECTIONS,TKSERVICEADDRESS.LATITUDEY,TKSERVICEADDRESS.ADDRESSLINE2,TKSERVICEADDRESS.STATEPROVINCE,TKSERVICEADDRESS.STREETADDRESS
    -> TimeDeltaCalculator
Note: Calculate the difference / between the query timestamp / and the CHANGEDATE
TimeDeltaCalculator: PythonCaller
    NEW_ATTRIBUTES = _delta_time
    PYTHONSOURCE:
      import fme
      import fmeobjects
      import datetime
      from datetime import timedelta
      import pytz

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              #self.bigTime = []
              pass
          def input(self,feature):
              try:
                  dateTimeFormat = '%Y-%m-%dT%H:%M:%S'    # Format for date-time conversion
                  timedelta(microseconds=1)

                  # Retrieve the query timestamp and Maximo CHANGEDATE (drop the timezone)
                  timestamp = datetime.datetime.strptime(feature.getAttribute("timestamp")[:-6],dateTimeFormat)
                  changeDate = datetime.datetime.strptime(feature.getAttribute("CHANGEDATE")[:-6],dateTimeFormat)

                  if not changeDate: return
                  seconds = (changeDate - timestamp).total_seconds()  # Calculate the time difference
                  #self.bigTime.append(changeDate)                     # Append to our list of tracked times / dates
                  feature.setAttribute("_delta_time",seconds)         # Post the result to new attribute
                  #print seconds, timestamp, changeDate

              except Exception, e:
                  print "Time conversion error: ",e
                  pass

              self.pyoutput(feature)

          def close(self):
              #now = datetime.datetime.now()

              #try:
              #    print self.bigTime
              #    youngest = max(dt for dt in self.bigTime if dt < now)
              #    newTimestamp = youngest + datetime.timedelta(microseconds=1)
              #    newTimestamp = youngest.isoformat()
              #    print youngest, newTimestamp.strftime("%Y-%m-%dT%H:%M:%S.%f%Z")

              #    timeFeature = fmeobjects.FMEFeature()
              #    timeFeature.setAttribute("xml_matched_element", "Timestamp")
              #    timeFeature.setAttribute("timestamp",newTimestamp)
              #    self.pyoutput(timeFeature)
              #except Exception, e:
              #    print "Exception in Close():", e
              pass
    PYTHONSYMBOL = FeatureProcessor
    -> ChangeTester
Note: Check for modification by / date and not by the / Maximo Integration User
ChangeTester: Tester
    BOOL_OP = COMPOSITE
    COMPOSITE_TEST = "1 AND (2 OR 3)"
    TEST_CLAUSE:
      TEST @Value(_delta_time) >= 0
      TEST @Value(MODIFYBY) NOT_ATTRIBUTE_HAS_VALUE ""
      TEST @Value(MODIFYBY) != $(MaxIntAdmin)
    PASSED -> AttributeCreator_2
    PASSED -> LogsAttachmentsLogger
LogsAttachmentsLogger: Logger
    LOG_FEATURE = LOG_RECORD
    MAXCOORDS = 20
    MAXFEATS = 20
    MESSAGE = Logs, Status, and Attachments are:
    SEVERITY = INFO
AttributeRemover_2
    REMOVE_ATTRS = numReferences
    -> IsDuplicate
    -> ServiceRequestLogger
IsDuplicate: Tester
    BOOL_OP = OR
    TEST_CLAUSE = TEST @Value(GLOBALTICKETID) ATTRIBUTE_HAS_VALUE ""
    PASSED -> ParentLookup
    FAILED -> AttributeCreator_2
ParentLookup
    GLOBALTICKETID = @Value(GLOBALTICKETID)
    MaximoServiceUrl = http://dwv-wamsapp4.richmondhill.local/meaweb/services/
    TRHFMEREQUESTID = @Value(TRHFMEREQUESTID)
    -> AttributeCreator_2
AttributeCreator_2
    ATTR_TABLE = SET_TO fme_feature_type = Message
    -> Junction
Note: SchemaMapper : Input
Junction
    -> Junction_2
ServiceRequestLogger: Logger
    LOG_FEATURE = LOG_RECORD
    MAXCOORDS = 20
    MAXFEATS = 20
    MESSAGE = Maximo Service Requests:
    SEVERITY = INFO
IgnoredMessageLogger: Logger
    LOG_FEATURE = LOG_RECORD
    MAXCOORDS = 20
    MAXFEATS = 20
    MESSAGE = Ignored Messages are:
    SEVERITY = INFO
XMLFragmenter_Fragments: Logger
    LOG_FEATURE = LOG_RECORD
    MAXCOORDS = 20
    MAXFEATS = 20
    MESSAGE = No messages to process:
    SEVERITY = INFO
MaximoLogger: Logger
    LOG_FEATURE = LOG_RECORD
    MAXCOORDS = 20
    MAXFEATS = 20
    MESSAGE = Logged Query Results from Maximo:
    SEVERITY = INFO
HTTPCaller__Rejected_: Logger
    LOG_FEATURE = LOG_RECORD
    MAXCOORDS = 20
    MAXFEATS = 20
    MESSAGE = Feature is:
    SEVERITY = INFO
    LOGGED -> Terminator
Terminator
    MESSAGE:
      This may have failed for the following reasons:
      - *There are no messages to retrieve from Maximo*
      - Maximo is not connected
      - The web service connection parameters have changed
      - SOAP message format has changed


      This is a scheduled process and will retry again.  If you see this message multiple times, then there is likely something wrong as above.
Note: Create ISO-formatted timestamp
AttributeCreator_3
    ATTR_TABLE = SET_TO timestamp = @DateTimeFormat(@DateTimeNow(local),%Y-%m-%dT%T%z)
    -> Junction_3
Note: Timestamp File Writer
Junction_3
    -> Junction_4

Bookmark: 2. Map Maximo Service Request to Canonical
  Extract all of the Maximo WORKLOG and COMLOG messages and changes to the Service Request into one set of JSON canonical messages.
Note: Step 1 : Input
Junction_2
    -> SchemaMapper
Note: Change to Canonical attribute names
SchemaMapper
    DATASET = $(SchemaMapper)
    FORMAT = XLSXR
    IDXDESTATTR = fme_feature_type
    IDXDESTCOL = ""
    IDXSOURCEATTR = fme_feature_type
    IDXSOURCECOL = ""
    MAP_ATTRS = Maximo Canonical """"""
    ROW_ID_ATTR = _schemamapper_row_ids
    TABLE = Mapping
    XLSXR_CONFIGURATION_DATASET = C:/FME/resources/data/Salesforce/CanonicalMapping.xlsx
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_SCAN_SCHEMA_IF_DYNAMIC = No
    XLSXR_SCHEMA = Mapping,0,Canonical,char,38,,,1,"Default Value",string,,,,2,Salesforce,char,41,,,3,Maximo,char,36,,,4,Description,char,77,,,5,F,char,114,,,1,,,,NO,NO,1,C:/FME/resources/data/Salesforce/CanonicalMapping.xlsx,"0,0,5,69",,NO
    XLSXR_TABLELIST = Mapping
    XLSXR_USE_SCHEMA_OTHER_FILES = No
    MAPPED -> SchemaMapper_Mapped
    MAPPED -> StatusMapper
    UNMAPPED -> StatusMapper
Note: Map the Maximo status / to Canonical
StatusMapper: AttributeValueMapper
    DIRECTION = Forward (Source To Destination)
    LUT = CLOSED,Closed,DUPLICATE,Duplicate,INPROG,In Progress,NEW,New,PENDING,Pending,QUEUED,Queued,REASSIGN,Reassigned,RESOLVED,Resolved
    SRC = STATUS
    VAL_ATTR = Status
    -> StatusMapper_Mapped
    -> AMPriorityMapper
Note: Update Case Type based on / Asset Management Priority
AMPriorityMapper: AttributeCreator
    ATTR_TABLE = SET_TO Type = @Value(TRHAMPRIORITY)
    -> AttributeExposer
Note: Expose canonical / model attributes
AttributeExposer
    ATTR_LIST = Asset_Id,AssignedGroup,AssignedTo,Attachment.Description,Attachment.Id,Attachment.Type,Attachment.URL,Attachment.urlType,Attachment.OwnerId,Attachment.OwnerObject,Block_Id,CloseReason,ClosedComments,Comment.CreateDate,Comment.CreatedBy,Comment.Description,Comment.Id,Comment.ModifiedBy,Comment.ModifiedDate,Comment.Subject,Comment.Type,Contact.AddressCity,Contact.AddressCountry,Contact.AddressPostalCode,Contact.AddressProvince,Contact.AddressStreet,Contact.AddressSuite,Contact.Email,Contact.FirstName,Contact.HomePhone,Contact.Id,Contact.LastName,Contact.OtherPhone,Description,Email.BccAddress,Email.Id,Email.Inbound,Email.MessageText,Email.ReplyTo,Email.SentFromAddress,Email.SentToAddress,Email.Subject,Email.ccAddress,OnHoldStatusReason,Parent_Id,RequestNumber,SR_QA.Acceptable_Metal_Items,SR_QA.Activity_Type,SR_QA.Cause_of_Damage,SR_QA.Duration_of_Work,SR_QA.Enter_Type_of_Dead_Animal,SR_QA.For_Fire_Request_Work_Order,SR_QA.Location_of_Damage,SR_QA.Name_of_Contractor_Utility,SR_QA.Preferred_Appliance_Pickup_Date,SR_QA.Size_of_Pothole,SR_QA.Type_of_Appliance,SR_QA.Type_of_Dumped_Item,SR_QA.Type_of_Item_Missed,SR_QA.Type_of_Truck,SR_QA.What_Was_Damaged,ServiceLocation.Address,ServiceLocation.City,ServiceLocation.Country,ServiceLocation.Details,ServiceLocation.Id,ServiceLocation.Latitude,ServiceLocation.Longitude,ServiceLocation.Parcel_Id,ServiceLocation.PostalCode,ServiceLocation.Province,ServiceLocation.Suite,Source_Request_Id,Status,Status.ChangeDate,Status.Memo,Subject,Target_Request_Id,Type,Ward_Id
    -> FormatTagRemover
Note: Script to strip RTF from text string
FormatTagRemover: PythonCaller
    PYTHONSOURCE:
      import fme
      import fmeobjects
      # Template Function interface:
      # When using this function, make sure its name is set as the value of
      # the 'Class or Function to Process Features' transformer parameter
      def processFeature(feature):
          pass

      # This class is used to parse HTML formatting tags into plain text
      # and properly takes care of line returns. This comes from the StackExchange:
      # https://stackoverflow.com/questions/328356/extracting-text-from-html-file-using-python
      from HTMLParser import HTMLParser
      from re import sub
      from sys import stderr
      from traceback import print_exc

      class _DeHTMLParser(HTMLParser):
          def __init__(self):
              HTMLParser.__init__(self)
              self.__text = []

          def handle_data(self, data):
              text = data.strip()
              if len(text) > 0:
                  text = sub('[ \t\r\n]+', ' ', text)
                  self.__text.append(text + ' ')

          def handle_starttag(self, tag, attrs):
              if tag == 'p' or tag == 'h1':
                  self.__text.append('\n\n')
              elif tag == 'br' or tag == 'h2' or tag == 'h3':
                  self.__text.append('\n')

          def handle_startendtag(self, tag, attrs):
              if tag == 'br':
                  self.__text.append('\n\n')

          def text(self):
              return ''.join(self.__text).strip()

      # Here is the function to call to instantiate the HTMLParser
      # class and properly parse the HTML-tagged text
      def dehtml(text):
          try:
              parser = _DeHTMLParser()
              parser.feed(text)
              parser.close()
              return parser.text()
          except:
              print_exc(file=stderr)
              return text

      # Uses several RegEx patterns to replace Rich Text Format comments and formatting directives
      # and produces plain text as output
      def deRtf(text):
          basicRtfPattern = "/\{\*?\\[^{}]+;}|[{}]|\\[A-Za-z]+\n?(?:-?\d+)?[ ]?/g"
          newLineSlashesPattern = "/\\\n/g"
          ctrlCharPattern = "/\n\\f[0-9]\s/g"

          #Remove RTF Formatting, replace RTF new lines with real line breaks, and remove whitespace
          text = text.replace(ctrlCharPattern,"").replace(basicRtfPattern,"").replace(newLineSlashesPattern,"\n").strip()
          return text.replace("<!-- RICH TEXT -->","")

      # Template Class Interface:
      # When using this class, make sure its name is set as the value of
      # the 'Class or Function to Process Features' transformer parameter
      class FeatureProcessor(object):
          def __init__(self):
              pass
          def input(self,feature):
              try:
                  attrNames = feature.getAllAttributeNames()     # Get all of the attribute names

                  # Search for attributes that may have HTML and/or RTF text
                  for name in attrNames:
                      if any([name == "Comment.Description", name == "Email.MessageText", name == "Status.Memo"]) :
                          attrValue = feature.getAttribute(name)  # get the attribute content
                          attrValue = dehtml(attrValue)           # remove HTML tags and replace newline characters
                          attrValue = deRtf(attrValue)            # remove RTF tags and replace newline characters
                          feature.setAttribute(name, attrValue)   # update the attribute content with plain text
              except Exception, e:
                  print "Exception caught:", e
                  pass

              self.pyoutput(feature)
          def close(self):
              pass
    PYTHONSYMBOL = FeatureProcessor
    -> Tester_2
Tester_2
    BOOL_OP = OR
    TEST_CLAUSE:
      CASE_INSENSITIVE_TEST @Value(Attachment.URL) CONTAINS '
      CASE_INSENSITIVE_TEST @Value(Attachment.Description) CONTAINS '
      CASE_INSENSITIVE_TEST @Value(DOCLINKS.DESCRIPTION) CONTAINS '
      CASE_INSENSITIVE_TEST @Value(DOCLINKS.URLNAME) CONTAINS '
      CASE_INSENSITIVE_TEST @Value(Status.Memo) CONTAINS '
      CASE_INSENSITIVE_TEST @Value(Comment.Description) CONTAINS '
      CASE_INSENSITIVE_TEST @Value(Comment.Subject) CONTAINS '
      CASE_INSENSITIVE_TEST @Value(Contact.LastName) CONTAINS '
      CASE_INSENSITIVE_TEST @Value(Contact.FirstName) CONTAINS '
    PASSED -> StringReplacer
    FAILED -> Sorter
StringReplacer
    CASE = NO
    FIND_TEXT = '
    NO_MATCH = _FME_NO_OP_
    REGEXP = NO
    REPLACE_TEXT = ''
    SRC_ATTRS = Attachment.Description,Attachment.URL,DOCLINKS.DESCRIPTION,Comment.Description,Contact.LastName,DOCLINKS.URLNAME,Comment.Subject,Contact.FirstName,Status.Memo
    -> Sorter
Note: Sort by the date of change / in case there are edits that / would overpost previous
Sorter
    SORT_PARM = CHANGEDATE ALPHA ASCENDING
    SORTED -> AttributeJSONPacker
AttributeJSONPacker
    ATTRS = Attachment.Description,Email.Subject,Contact.AddressStreet,Contact.FirstName,Comment.Subject,Email.Inbound,Type,ServiceLocation.Province,Email.ReplyTo,Contact.AddressPostalCode,Email.Id,Comment.Type,Parent_Id,Contact.Email,ServiceLocation.Suite,Comment.ModifiedBy,Contact.AddressProvince,Status,Contact.HomePhone,Contact.AddressCity,Email.ccAddress,ServiceLocation.Details,Source_Request_Id,ClosedComments,Comment.Id,Attachment.Id,Attachment.URL,Asset_Id,Email.SentFromAddress,CloseReason,ServiceLocation.Id,AssignedTo,Target_Request_Id,Contact.OtherPhone,Comment.CreateDate,Email.MessageText,ServiceLocation.Address,Comment.Description,Contact.AddressSuite,OnHoldStatusReason,ServiceLocation.Longitude,Status.Memo,Block_Id,ServiceLocation.Country,ServiceLocation.City,Comment.ModifiedDate,Email.BccAddress,Email.SentToAddress,Attachment.urlType,Status.ChangeDate,Comment.CreatedBy,Contact.AddressCountry,Attachment.OwnerObject,Contact.LastName,ServiceLocation.Latitude,ServiceLocation.PostalCode,Attachment.Type,Attachment.OwnerId
    PACKED = _packed
    -> DuplicateFilter
Note: Remove any duplicate messages / (if they were somehow generated)
DuplicateFilter
    INPUT_ORDERED_CHOICE = No
    KEYATTR = _packed
    UNIQUE -> AttributeExposer_3
AttributeExposer_3
    ATTR_LIST = _packed
    -> SQLExecutor [INITIATOR]
Note: Remove null fields or / objects from the JSON / output
JSONFormatter
    ERROR_LIST_ATTR = _json_error
    FORMAT = Pretty Print
    INDENT_STYLE = 3 spaces
    JSON_DOCUMENT = @Value(_packed)
    OUTPUT_ATTR = _packed
    OUTPUT_ENCODING = UTF-8
    READ_FROM_FILE = NO
    REMOVE_EMPTY_OBJECTS_AND_ARRAYS = Yes
    REMOVE_EMPTY_STRINGS = Yes
    REMOVE_NULLS = Yes
    -> AttributeKeeper_3
    -> MessageLogger
AttributeKeeper_3
    KEEP_ATTRS = xml_matched_element,CHANGEDATE,_packed
    -> ListBuilder_2
Note: Combine all features into a single list
ListBuilder_2
    GROUPS_ORDERED = No
    GROUP_BY = xml_matched_element
    LIST_NAME = ListOfCanonicalJson
    -> ListConcatenator_2
Note: Convert the list to a comma separated text
ListConcatenator_2
    DROP_EMPTY_PARTS = Yes
    LIST_ATTR = ListOfCanonicalJson{}._packed
    SEP = ,
    VAL_ATTR = CanonicalList
    -> AttributeCreator
AttributeCreator
    ATTR_TABLE = SET_TO CanonicalList = [@Value(CanonicalList)]
    -> TestFilter_2
Note: Split based upon message type / NOTE: Disabled COMLOG Text
TestFilter_2
    DEFAULT_VALUE = <UNFILTERED>
    TEST_LIST = BOOL_OP,OR,COMPOSITE_TEST,<Unused>,TEST_CLAUSE,"TEST @Value(xml_matched_element) = WORKLOG",WORKLOG,BOOL_OP,OR,COMPOSITE_TEST,<Unused>,TEST_CLAUSE,"TEST @Value(xml_matched_element) = TKSTATUS",TKSTATUS,BOOL_OP,OR,COMPOSITE_TEST,<Unused>,TEST_CLAUSE,"TEST @Value(xml_matched_element) = COMLOG",COMLOG,BOOL_OP,OR,COMPOSITE_TEST,<Unused>,TEST_CLAUSE,"TEST @Value(xml_matched_element) = DOCLINKS",DOCLINKS,BOOL_OP,OR,COMPOSITE_TEST,<Unused>,TEST_CLAUSE,"TEST @Value(xml_matched_element) = SR",SR
    WORKLOG -> CommentNotifier
    TKSTATUS -> CommentNotifier
    COMLOG -> CommentNotifier
    SR -> SRNotifier
Note: Notify SRUpdateFromMaximo or CommentFromMaximo topics
CommentNotifier: FMEServerNotifier
    BODY = @Value(CanonicalList)
    SERVER_CONNECTION = $(SERVER_CONNECTION)
    TOPIC = CommentsFromMaximo
    -> TopicItemLogger
    -> ListExploder
    <REJECTED> -> Terminator_2
TopicItemLogger: Logger
    LOG_FEATURE = LOG_RECORD
    MAXCOORDS = 20
    MAXFEATS = 20
    MESSAGE = Canonical List sent to topic:
    SEVERITY = INFO
SRNotifier: FMEServerNotifier
    BODY = @Value(CanonicalList)
    SERVER_CONNECTION = $(SERVER_CONNECTION)
    TOPIC = SRUpdateFromMaximo
    -> TopicItemLogger_SR
    -> ListExploder
    -> Emailer
    <REJECTED> -> Terminator_2
ListExploder
    ATTR_ACCUM_MODE = Merge List Attributes
    ATTR_CONFLICT_RES = Use List Attribute Values
    INDEX_ATTR = _element_index
    LIST_ATTR = ListOfCanonicalJson{}
    ELEMENTS -> Sorter_2
Sorter_2
    SORT_PARM = CHANGEDATE ALPHA DESCENDING
    SORTED -> Counter
Counter
    CNT_ATTR = _count
    DOMAIN = counter
    SCOPE = Global
    START = 0
    -> Tester
Tester
    BOOL_OP = OR
    TEST_CLAUSE = TEST @Value(_count) = 0
    PASSED -> AttributeCreator_5
AttributeCreator_5
    ATTR_TABLE = SET_TO timestamp = @Value(CHANGEDATE)
    -> Timestamp (writer FFS_1)
Terminator_2
    MESSAGE = There may be connection issues in FME Server, or the topic for CommentsFromMaximo or SRUpdateFromMaximo may not exist!
TopicItemLogger_SR: Logger
    LOG_FEATURE = LOG_RECORD
    MAXCOORDS = 20
    MAXFEATS = 20
    MESSAGE = Canonical List sent to topic:
    SEVERITY = INFO
Emailer [off]
    ATTACHGROUP = No
    BODY:
      CanonicalList = @Value(CanonicalList)

      _notifier_topic = @Value(_notifier_topic)

      _notifier_content = @Value(_notifier_content)
    FROM = noreply@richmondhill.ca
    SERVICE = Generic SMTP
    SMTP_CONNECTION = SMTP_GROUP;;HOST;relay.richmondhill.local;PORT;25;ENCRYPTION;None;TIMEOUT;60;AUTHENTICATION;NO;USERNAME;<Unused>;PASSWORD;<Unused>;FME_CONTROLLER_QUERY_FILE;transformers\dependencies\emailer\Generic SMTP.fme
    SUBJECT = From Max to SF
    TO = jimmy.chao@richmondhill.ca
MessageLogger: Logger
    LOG_FEATURE = LOG_RECORD
    MAXCOORDS = 20
    MAXFEATS = 20
    MESSAGE = JSON Message Output:
    SEVERITY = INFO
StatusMapper_Mapped: Logger
    LOG_FEATURE = LOG_RECORD
    MAXCOORDS = 20
    MAXFEATS = 20
    MESSAGE = Status Mapped is:
    SEVERITY = INFO
SchemaMapper_Mapped: Logger
    LOG_FEATURE = LOG_RECORD
    MAXCOORDS = 20
    MAXFEATS = 20
    MESSAGE = Schema Mapped is:
    SEVERITY = INFO
Note: Timestamp file DNE, create new
Junction_4
    -> Timestamp (writer FFS_1)
Note: Add a new timestamp file / with the timestamp record used / at the beginning in query to Maximo
Timestamp (writer FFS_1)
    attributes: timestamp datetime

FME custom transformer ParentLookup
This transformer takes the GLOBALTICKETID value and looks up in Maximo for the related record, replacing this value with the Salesforce Case Id

Parameters:
- GLOBALTICKETID = @Value(GLOBALTICKETID)
- TRHFMEREQUESTID = @Value(TRHFMEREQUESTID)
- MaximoServiceUrl = http://dwv-wamsapp4.richmondhill.local/meaweb/services/   # Maximo Server URL

Input (input)
    -> SOAPFormatter_2
Note: Build the query to Maximo that retrieves / the Parent Service Request
SOAPFormatter_2: AttributeCreator
    ATTR_TABLE:
      SET_TO xmlToQuery = <soapenv:Envelope xmlns:soapenv="http://schemas.xmlsoap.org/soap/envelope/" xmlns:max="http://www.ibm.com/maximo">
          <soapenv:Header/>
           <soapenv:Body>
        	<max:QueryTRHFMESR xmlns:max="http://www.ibm.com/maximo" creationDateTime="2008-09-28T21:49:45" baseLanguage="EN" uniqueResult="0" rsStart="0">
          	  <max:TRHFMESRQuery>
            	  	<max:WHERE>TRHFMEREQUESTID is not null AND TICKETID = '@Value(GLOBALTICKETID)'</max:WHERE>
        	  </max:TRHFMESRQuery>
        	</max:QueryTRHFMESR>
        	</soapenv:Body>
        </soapenv:Envelope>
    -> BulkAttributeRenamer
BulkAttributeRenamer
    ATTRCHOICE = All Attributes
    MODE_CHOICE = RENAME
    PATTERN_ACTION_DISP = ADDPREFIX
    REPLACE_STR = SR.
    -> HTTPCaller_2
Note: Call the Maximo web service / to retrieve records that match / the query
HTTPCaller_2
    AUTH_METHOD = Web Connection
    AUTH_NAMED_CONNECTION = Maximo
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(MaximoServiceUrl)/TRHFMESYS_TRHFMESRQUERYES
    TRANSFER_TIMEOUT_LENGTH = 90
    UPLOAD_BODY = @Value(SR.xmlToQuery)
    UPLOAD_CONTENT_TYPE = text/xml
    UPLOAD_TYPE = Specify Upload Body
    USE_COOKIES = No
    VERIFY_SSL_CERTIFICATES = Yes
    -> XMLFragmenter_2
    <REJECTED> -> BulkAttributeRenamer_2
Note: Extract the message components for: / - Service Request (SR)
XMLFragmenter_2
    ATTRIBUTE_XML = _response_body
    EMBEDDED_EXPRESSIONS = TRHFMEREQUESTID
    FEATURE_TYPES_FORMAT_NAME = XML
    FLATTEN_OPTIONS:
      <structure
      separator="."
      open-list-brace="{"
      close-list-brace="}"
      map-empty-elements="yes"
      matched-prefix="yes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    MERGE_ATTRS = Yes
    NEW_ATTRIBUTES = TRHFMEREQUESTID
    XML_SOURCE_TYPE = Attribute with XML document
    FRAGMENTS -> AttributeCreator
Note: Update the GLOBALTICKETID to / indicate the Salesforce Parent Case
AttributeCreator
    ATTR_TABLE = SET_TO SR.GLOBALTICKETID = @Value(TRHFMEREQUESTID)
    -> BulkAttributeRenamer_2
BulkAttributeRenamer_2
    ATTRCHOICE = All Attributes
    CASE_DISP = YES
    MODE_CHOICE = RENAME
    PATTERN_ACTION_DISP = REMOVEPREFIX
    REPLACE_STR = SR.
    -> Output (output)
    -> ParentLookupLogger
ParentLookupLogger: Inspector [off]
Output (output)

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
Input Ports
    Input
Accepts any feature.
    Output Ports
    Output
Ouputs the original feature with an added attribute containing the JSON object.
    Parameters
    Attributes to Pack
    Specific attributes to pack. Chosing any attributes will disable the filter (described below).
    Filter Prefix
All attributes with this prefix will be added to the packed attribute. Leaving this value blank will pack all the attributes.
    Packed Attribute Name
The name of the new attribute containing the packed values

Parameters:
- FILTER =   # Filter Prefix (blank for all attributes)
- PACKED = _packed   # Packed Attribute Name
- ATTRS =   # " " Attributes to Pack

Input (input)
    -> ParameterFetcher
Note: Get filter value
ParameterFetcher
    ATTR_LIST = AttributeJSONPacker_FILTER {$(FILTER)} AttributeJSONPacker_PACKED {$(PACKED)} AttributeJSONPacker_ATTRS {$(ATTRS)}
    -> PythonCaller
PythonCaller
    NEW_ATTRIBUTES = $(PACKED)
    PYTHONSOURCE:
      from __future__ import absolute_import, division, print_function, unicode_literals

      import fmeobjects
      import binascii
      import json
      import six

      # This class will create a packed list of format
      # attributes suitable for use with @SupplyAttributes()

      def packIgdsAtts(feature):
         # get a list of attribute names
         attlist = feature.getAllAttributeNames()
         attlist = map(six.text_type, attlist)

         # get attributes to pack
         pack_attrs = feature.getAttribute('AttributeJSONPacker_ATTRS').replace('"', '').strip().split(',')

         # get filter value
         filter = feature.getAttribute('AttributeJSONPacker_FILTER')


         # get packed attribute name
         packedAtt = feature.getAttribute('AttributeJSONPacker_PACKED')

         addedAttrs = {
            'AttributeJSONPacker_ATTRS',
            'AttributeJSONPacker_FILTER',
            'AttributeJSONPacker_PACKED',
         }

         # disable filter if packed attribute chosen
         if pack_attrs[0] != "":
             filter = False

         # create dict for packed attributes
         packed = {}

         # loop through attribute names
         for att in attlist:
             if ((filter and filter in att) or att in pack_attrs) and att not in addedAttrs:
                 att_value = feature.getAttribute(att)
                 float_val, int_val = None, None
                 try:
                     float_val = float(att_value)
                     int_val = int(att_value)
                     if int_val == float_val:
                         att_value = int_val
                     else:
                         att_value = float_val
                 except ValueError as e:
                     if int_val is not None:
                         att_value = int_val
                     if float_val is not None:
                         att_value = float_val

                 # convert binary attributes to hex for storage
                 if type(att_value) == bytearray:
                     att_value = "0x" + binascii.hexlify(att_value)
                 # append attribute value
                 packed[att] = att_value

         #add packed attributes in JSON format
         feature.setAttribute(packedAtt,json.dumps(packed,separators=(',', ':'), ensure_ascii=False))
    PYTHONSYMBOL = packIgdsAtts
    -> Output (output)
Output (output)
