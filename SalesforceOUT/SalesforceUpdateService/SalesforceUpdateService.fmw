FME workspace SalesforceUpdateService.fmw

Parameters:
- SourceDataset_TEXTLINE = SalesforceUpdateService   # Source Text File(s)
- SalesforceMaximoUser = Integration User   # Enter the full name (first and last) of the Maximo integration user for Salesforce
- SALESFORCE_OBJECT_ID = 0120v0000000CkiAAE   # Salesforce Object Identifier
- SALESFORCE_OBJECT_TYPE = RecordType   # Salesforce Object Type
- SchemaMapper = $(FME_SHAREDRESOURCE_DATA)\Salesforce\CanonicalMapping.xlsx   # "" Field mapping file with canonical model

Readers:
- TEXTLINE_1: TEXTLINE from $(SourceDataset_TEXTLINE)

text_line (reader TEXTLINE_1)
    attributes: text_line_data buffer
    -> JSONFlattener
Note: Convert topic content to JSON
JSONFlattener
    ERROR_LIST_ATTR = _json_error
    JSON_DOCUMENT = @Value(text_line_data)
    NEW_ATTRIBUTES = ws_topic opt_topic array{}
    READ_FROM_FILE = NO
    RECURSIVE = Yes
    -> ListExploder
    -> Junction_5
Note: Convert array to features / if we received an array
ListExploder
    ATTR_ACCUM_MODE = Merge List Attributes
    ATTR_CONFLICT_RES = Use List Attribute Values
    INDEX_ATTR = _element_index
    LIST_ATTR = array{}
    ELEMENTS -> AttributeExposer_2
    <REJECTED> -> AttributeExposer_2
Note: Expose attributes of the / canonical service request
AttributeExposer_2
    ATTR_LIST = Asset_Id,AssignedGroup,Attachment.Description,Attachment.Id,Attachment.Type,Attachment.URL,Attachment.urlType,Block_Id,CloseReason,Comment.Description,Comment.Id,Comment.Subject,Comment.Type,Contact.AddressCity,Contact.AddressCountry,Contact.AddressPostalCode,Contact.AddressProvince,Contact.AddressStreet,Contact.AddressSuite,Contact.Email,Contact.FirstName,Contact.HomePhone,Contact.LastName,Contact.OtherPhone,Description,Email.BccAddress,Email.Id,Email.Inbound,Email.MessageText,Email.ReplyTo,Email.SentFromAddress,Email.SentToAddress,Email.Subject,Email.ccAddress,OnHoldStatusReason,Parent_Id,SR_QA.Acceptable_Metal_Items,SR_QA.Activity_Type,SR_QA.Cause_of_Damage,SR_QA.Duration_of_Work,SR_QA.Enter_Type_of_Dead_Animal,SR_QA.For_Fire_Request_Work_Order,SR_QA.Location_of_Damage,SR_QA.Name_of_Contractor_Utility,SR_QA.Other_Appliance_Question,SR_QA.Preferred_Appliance_Pickup_Date,SR_QA.Size_of_Pothole,SR_QA.Type_of_Appliance,SR_QA.Type_of_Dumped_Item,SR_QA.Type_of_Item_Missed,SR_QA.Type_of_Truck,SR_QA.What_Was_Damaged,ServiceLocation.Id,ServiceLocation.Address,ServiceLocation.City,ServiceLocation.Country,ServiceLocation.Latitude,ServiceLocation.Longitude,ServiceLocation.Parcel_Id,ServiceLocation.PostalCode,ServiceLocation.Province,ServiceLocation.Suite,Source_Request_Id,Status,Status.Memo,Subject,AssignedTo,Target_Request_Id,Type
    -> Junction_7
    -> AttributeCopier
AttributeCopier
    ATTR_TABLE = COPY Source_Request_Id > _SFID
    -> SQLExecutor_5 [INITIATOR]
Note: Add to Queue
SQLExecutor_5
    COMBINE_ATTRS = Keep Initiator Attributes if Conflict
    COMBINE_GEOM = Initiator Geometry Only
    DATASET = TWV-SQL3_QueueDB
    FORMAT = MSSQL_ADO
    MSSQL_ADO_COMMAND_TIMEOUT = 60
    MSSQL_ADO_NAMED_CONNECTION = TWV-SQL3_QueueDB
    MSSQL_ADO_QUERY_FEATURE_TYPES_FOR_MERGE_FILTERS = Yes
    SQL_STATEMENT:
      FME_SQL_DELIMITER ;
      UPDATE dbo.[fme_case_queue]
      SET [status] = 'SFUpdating', [process_date] = CURRENT_TIMESTAMP, [job_id] = $(FME_JOB_ID)
      WHERE [date_added] = (SELECT MIN([date_added])
                          FROM dbo.[fme_case_queue]
                          WHERE [salesforce_id] = '@Value(_SFID)'
                          AND ([status] = 'ReturnToSF' OR [status] = 'ReturnId' OR [status] = 'SFUpdating'));
    INITIATOR -> OwnerIdSetter
    <REJECTED> -> SQLExecutor_5_rejected
OwnerIdSetter
    ASSIGNEDTO = @Value(AssignedTo)
    PARENT_ID = @Value(Parent_Id)
    STATUS = @Value(Status)
    STATUS.MEMO = @Value(Status.Memo)
    SalesforceMaximoUser = $(SalesforceMaximoUser)
    TARGET_REQUEST_ID = @Value(Target_Request_Id)
    Mapped -> SchemaMapper
    Unmapped -> SchemaMapper
Note: Map the canonical model / to the Salesforce model
SchemaMapper
    DATASET = $(SchemaMapper)
    FORMAT = XLSXR
    IDXDESTATTR = fme_feature_type
    IDXDESTCOL = ""
    IDXSOURCEATTR = fme_feature_type
    IDXSOURCECOL = ""
    MAP_ATTRS = Canonical Salesforce $(FME_ASC_16)
    ROW_ID_ATTR = _schemamapper_row_ids
    TABLE = Mapping
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_SCAN_SCHEMA_IF_DYNAMIC = No
    XLSXR_USE_SCHEMA_OTHER_FILES = No
    MAPPED -> SchemaMapper_Mapped
    MAPPED -> StatusValueMapper
    UNMAPPED -> Junction_13
    UNMAPPED -> StatusValueMapper
SchemaMapper_Mapped: Logger
    LOG_FEATURE = LOG_RECORD
    MAXCOORDS = 20
    MAXFEATS = 20
    MESSAGE = Feature is:
    SEVERITY = INFO
Note: Map the status for canonical / model to Salesforce model
StatusValueMapper: AttributeValueMapper
    DIRECTION = Forward (Source To Destination)
    LUT = In Progress,In Progress,Closed,Closed,Duplicate,FME_NULL_VALUE,New,New,Pending,New,Queued,In Progress,Reassigned,FME_NULL_VALUE,Resolved,Closed
    SRC = Status
    VAL_ATTR = Status
    -> AttributeExposer
Note: Expose the mapped / Salesforce case fields
AttributeExposer
    ATTR_LIST = Id,CaseComment.CommentBody,Owner,Parent_Id,Reason,RecordType.DeveloperName,Status,TRH_Asset_ID__c,TRH_Block_Number__c,TRH_Maximo_Assignee_Name__c,TRH_Latitude__c,TRH_Longitude__c,TRH_Postal_Code__c,TRH_Problem_or_Service_City__c,TRH_Problem_or_Service_Country__c,TRH_Problem_or_Service_Province__c,TRH_Problem_or_Service_Street__c,TRH_Additional_Location_Details__c,TRH_Unit__c,TRH_WAMS_Id__c,Type,Source_Request_Id
    -> TestFilter
Note: Check if the Service Location / Identifier is populate...
TestFilter
    DEFAULT_VALUE = <UNFILTERED>
    TEST_LIST = BOOL_OP,OR,COMPOSITE_TEST,<Unused>,TEST_CLAUSE,"TEST @Value(TRH_Asset_ID__c) ATTRIBUTE_HAS_VALUE """"",ASSET,BOOL_OP,AND,COMPOSITE_TEST,<Unused>,TEST_CLAUSE,"TEST @Value(ServiceLocation.Id) ATTRIBUTE_HAS_VALUE """"",LOCATION
    ASSET -> AttributeRenamer_OUTPUT_-__Junction_3
    LOCATION -> AttributeRenamer
    <UNFILTERED> -> AttributeRenamer_OUTPUT_-__Junction_3
Note: ... and map service location id / to asset id in Salesforce
AttributeRenamer
    ATTR_TABLE = RENAME_SET_DEFAULT ServiceLocation.Id > TRH_Asset_ID__c
    -> AttributeRenamer_OUTPUT_-__Junction_3
AttributeRenamer_OUTPUT_-__Junction_3: Junction
    -> Junction_3
    -> Junction
Note: AttributeJSONPacker : Input
Junction
    -> Junction_2
Note: AttributeExposer : Output
Junction_2
    -> LeadZeroReplacer
Note: Ensure the block number / is an integer
LeadZeroReplacer: AttributeCreator
    ATTR_TABLE = SET_TO TRH_Block_Number__c = @ReplaceRegEx(@Value(TRH_Block_Number__c),"^0+","")
    -> AttributeReprojector
Note: Reproject back into / geographic space
AttributeReprojector
    DEST = LL84
    SOURCE = UTM84-17N
    XATTR = TRH_Longitude__c
    YATTR = TRH_Latitude__c
    -> AttributeRemover
AttributeRemover
    REMOVE_ATTRS = Contact.Email,Email.MessageText,SR_QA.For_Fire_Request_Work_Order,Attachment.Description,Target_Request_Id,IsReassigned,SR_QA.Type_of_Dumped_Item,_schemamapper_row_ids,CloseReason,Comment.Description,Contact.AddressProvince,ServiceLocation.PostalCode,Email.ccAddress,ServiceLocation.Longitude,Contact.AddressCountry,Attachment.Type,_element_index,ServiceLocation.Province,Email.Subject,ServiceLocation.Address,Contact.OtherPhone,ws_topic,SR_QA.Type_of_Appliance,Email.BccAddress,Attachment.Id,Comment.Subject,Contact.AddressSuite,SR_QA.Acceptable_Metal_Items,AssignedTo,Contact.FirstName,Email.Id,SalesforceMaximoUser,text_line_data,Contact.HomePhone,SR_QA.Type_of_Item_Missed,ServiceLocation.Parcel_Id,SR_QA.Activity_Type,SR_QA.What_Was_Damaged,Email.SentToAddress,Comment.Type,SR_QA.Size_of_Pothole,Block_Id,Email.Inbound,Contact.LastName,Status.Memo,ServiceLocation.Country,SR_QA.Cause_of_Damage,fme_rejection_code,Attachment.URL,opt_topic,SR_QA.Other_Appliance_Question,Description,Asset_Id,ServiceLocation.Latitude,ServiceLocation.City,SR_QA.Enter_Type_of_Dead_Animal,SR_QA.Type_of_Truck,Attachment.urlType,ServiceLocation.Suite,SR_QA.Location_of_Damage,Email.ReplyTo,Contact.AddressStreet,array,SR_QA.Duration_of_Work,AssignedGroup,Comment.Id,Contact.AddressPostalCode,SR_QA.Preferred_Appliance_Pickup_Date,Contact.AddressCity,Email.SentFromAddress,SR_QA.Name_of_Contractor_Utility,Subject
    -> Junction_15
    -> AttributeJSONPacker
AttributeJSONPacker
    ATTRS = TRH_Additional_Location_Details__c,OnHoldStatusReason,TRH_Postal_Code__c,TRH_Problem_or_Service_Province__c,Type,TRH_Longitude__c,OwnerId,Parent_Id,TRH_Duplicate__c,TRH_Problem_or_Service_Country__c,TRH_WAMS_Id__c,Status,TRH_Problem_or_Service_City__c,TRH_Unit__c,TRH_Asset_ID__c,TRH_Block_Number__c,TRH_Maximo_Assignee_Name__c,TRH_Problem_or_Service_Street__c,Reason,TRH_Latitude__c
    PACKED = _packed
    -> AttributeExposer_4
AttributeExposer_4
    ATTR_LIST = _packed
    -> JSONFormatter
Note: Remove null fields or / objects from the JSON / output
JSONFormatter
    ERROR_LIST_ATTR = _json_error
    FORMAT = Linearize
    JSON_DOCUMENT = @Value(_packed)
    OUTPUT_ATTR = _packed
    OUTPUT_ENCODING = UTF-8
    READ_FROM_FILE = NO
    REMOVE_EMPTY_OBJECTS_AND_ARRAYS = Yes
    REMOVE_EMPTY_STRINGS = Yes
    REMOVE_NULLS = Yes
    -> CheckReassigned
Note: Remove the Maximo Id (set to "") / if the Status was Reassigned
CheckReassigned: AttributeCreator
    ATTR_TABLE = SET_TO _packed = FME_CONDITIONAL:DEFAULT_VALUE'_FME_NO_OP_'BOOL_OP;OR;COMPOSITE_TEST;<Unused>;TEST @Value(_packed) NOT_CONTAINS TRH_WAMS_Id'@ReplaceString(@Value(_packed),},","TRH_WAMS_Id__c":""}")'FME_NUM_CONDITIONS2___
    -> AttributeKeeper_3
AttributeKeeper_3
    KEEP_ATTRS = _SFID,Id,Source_Request_Id,_packed
    -> JSONValidator
JSONValidator
    ERROR_LIST_ATTR = _json_error
    JSON_DOCUMENT = @Value(_packed)
    READ_FROM_FILE = NO
    PASSED -> SalesforceConnector
SalesforceConnector
    API_VERSION = Latest
    CONNECTION = CRMTRHSalesforce
    INCLUDE_DELETED = NO
    SOQL = Select Id from Case WHERE Id = '@Value(Id)'
    -> SFVersion
    <REJECTED> -> Terminator_3
Terminator_3
    MESSAGE = Translation Terminated
SFVersion: SubstringExtractor
    END = 19
    RESULT_ATTR = _SFVersion
    SRC_STRING = @Value(salesforce_record_url)
    START = 15
    -> AttributeKeeper
AttributeKeeper
    KEEP_ATTRS = _SFVersion,salesforce_instance_url,_SFID,Id,_packed
    -> HTTPCaller_2
Note: PATCH updated Case / to Salesforce.com
HTTPCaller_2
    AUTH_METHOD = Web Connection
    AUTH_NAMED_CONNECTION = CRMTRHSalesforce
    CONNECTION_TIMEOUT_LENGTH = 60
    ERROR_ATTR = _error
    FOLLOW_REDIRECTS = Yes
    HTTP_METHOD = PATCH
    RESPONSE_HEADER_LIST_ATTR = _headers
    SAVE_FILE = Attribute
    STATUS_CODE_ATTR = _http_status_code
    TARGET_ATTR = _response_body
    TARGET_ATTR_ENCODING = auto-detect
    TARGET_URL = @Value(salesforce_instance_url)/services/data/@Value(_SFVersion)/sobjects/Case/@Value(Id)
    TRANSFER_TIMEOUT_LENGTH = 90
    UPLOAD_BODY = @Value(_packed)
    UPLOAD_CONTENT_TYPE = JSON (application/json)
    UPLOAD_TYPE = Specify Upload Body
    USE_COOKIES = No
    VERIFY_SSL_CERTIFICATES = No
    -> SQLExecutor_4 [INITIATOR]
    <REJECTED> -> FeatureHolder
Note: Delete row from queue
SQLExecutor_4
    COMBINE_ATTRS = Keep Initiator Attributes if Conflict
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT = DELETE FROM dbo.[fme_case_queue] WHERE [status] = 'SFUpdating' AND [salesforce_id] = '@Value(_SFID)'
    RESULT -> Logger
    INITIATOR -> Logger
    <REJECTED> -> Terminator_4
Logger
    LOG_FEATURE = LOG_RECORD
    MAXCOORDS = 20
    MAXFEATS = 20
    MESSAGE:
      Case Upsert result:
      Id = @Value(Id)
    SEVERITY = INFO
Terminator_4
    MESSAGE = There was an issue deleting record from the Case Queue table
Note: Make sure all features are / processed through API call / to Salesforce before processing / any error messages
FeatureHolder
    -> JSONFlattener_3
JSONFlattener_3
    ERROR_LIST_ATTR = _json_error
    JSON_DOCUMENT = @Value(_response_body)
    NEW_ATTRIBUTES = array{0}.errorCode
    READ_FROM_FILE = NO
    RECURSIVE = Yes
    -> EntityDeletedTester
    <REJECTED> -> JSONFlattener_3_Rejected
Note: If the Case was deleted, ignore / this error and log. Otherwise terminate.
EntityDeletedTester: TestFilter
    DEFAULT_VALUE = OtherError
    TEST_LIST:
      BOOL_OP,OR,COMPOSITE_TEST,<Unused>,TEST_CLAUSE,"TEST @Value(array{0}.errorCode) = ENTITY_IS_DELETED
      TEST @Value(array{0}.errorCode) = INVALID_CROSS_REFERENCE_KEY",CaseDeletedIgnore
    CaseDeletedIgnore -> SQLExecutor_2 [INITIATOR]
    OtherError -> SQLExecutor_3 [INITIATOR]
Note: Delete row from queue
SQLExecutor_2
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT = DELETE FROM dbo.[fme_case_queue] WHERE [status] = 'SFUpdating' AND [salesforce_id] = '@Value(_SFID)'
    RESULT -> HTTPCaller_2__Rejected_
    <REJECTED> -> HTTPCaller_2__Rejected_
JSONFlattener_3_Rejected: Logger
    LOG_FEATURE = LOG_RECORD
    MAXCOORDS = 20
    MAXFEATS = 20
    MESSAGE = Feature is:
    SEVERITY = INFO
    LOGGED -> SQLExecutor_3 [INITIATOR]
Note: Update queue status
SQLExecutor_3
    COMBINE_ATTRS = Result Attributes Only
    COMBINE_GEOM = Initiator Geometry Only
    DATASET = TWV-SQL3_QueueDB
    FORMAT = MSSQL_ADO
    MSSQL_ADO_COMMAND_TIMEOUT = 30
    MSSQL_ADO_NAMED_CONNECTION = TWV-SQL3_QueueDB
    MSSQL_ADO_QUERY_FEATURE_TYPES_FOR_MERGE_FILTERS = Yes
    SQL_STATEMENT:
      FME_SQL_DELIMITER ;
      UPDATE dbo.[fme_case_queue]
      SET [status] = 'Failed'
      WHERE ([status] = 'SFUpdating' OR [status] = 'ReturnId' OR [status] = 'ReturnToSF') AND [salesforce_id] = '@Value(_SFID)';
    RESULT -> Terminator
    INITIATOR -> HTTPCaller_2__Rejected_
    INITIATOR -> Terminator
    <REJECTED> -> Terminator
    <REJECTED> -> HTTPCaller_2__Rejected_
HTTPCaller_2__Rejected_: Logger
    LOG_FEATURE = LOG_RECORD
    MAXCOORDS = 20
    MAXFEATS = 20
    MESSAGE:
      Salesforce HTTP error is:
      @Value(_response_body)
    SEVERITY = ERROR
Terminator
    MESSAGE:
      There may be an issue connecting to Salesforce or with the content of the message being posted:
      @Value(_response_body)
Note: CaseWriter_Log : Input
Junction_15
    -> Junction_16
Note: AttributeExposer_Output : Input
Junction_3
    -> Junction_4
Note: SchemaMapper_Unmapped : Input
Junction_13
    -> Junction_14
SQLExecutor_5_rejected: Logger
    LOG_FEATURE = LOG_ONLY
    MAXCOORDS = 20
    MAXFEATS = 20
    MESSAGE = There was an issue inserting into the Case Queue table
    SEVERITY = ERROR
    LOGGED -> Terminator_2
Terminator_2
    MESSAGE = Translation Terminated: SQL Executor Failed
Note: ReceivedServiceRequest : Input
Junction_7
    -> Junction_8
Note: JSONFlattener_Output : Input
Junction_5
    -> Junction_6

Bookmark: Log Messages
  Log output and error messages
Note: AttributeRemover : Output
Junction_16
    -> CaseWriter_Log
CaseWriter_Log: Logger
    LOG_FEATURE = LOG_RECORD
    MAXCOORDS = 20
    MAXFEATS = 20
    MESSAGE = Feature Written to Salesforce is:
    SEVERITY = INFO
Note: AttributeExposer : Output
Junction_4
    -> AttributeExposer_Output
AttributeExposer_Output: Logger
    LOG_FEATURE = LOG_RECORD
    MAXCOORDS = 20
    MAXFEATS = 20
    MESSAGE = Feature is:
    SEVERITY = INFO
Note: SchemaMapper : Unmapped
Junction_14
    -> SchemaMapper_Unmapped
SchemaMapper_Unmapped: Logger
    LOG_FEATURE = LOG_RECORD
    MAXCOORDS = 20
    MAXFEATS = 20
    MESSAGE = Unmapped Features are:
    SEVERITY = INFO
Note: AttributeExposer_2 : Output
Junction_8
    -> ReceivedServiceRequest
ReceivedServiceRequest: Logger
    LOG_FEATURE = LOG_RECORD
    MAXCOORDS = 20
    MAXFEATS = 20
    MESSAGE = Canonical Service Request Is:
    SEVERITY = INFO
Note: JSONFlattener : Output
Junction_6
    -> JSONFlattener_Output
JSONFlattener_Output: Logger
    LOG_FEATURE = LOG_RECORD
    MAXCOORDS = 20
    MAXFEATS = 20
    MESSAGE = Feature is:
    SEVERITY = INFO

Bookmark: 2. PATCH Update to Salesforce
  PATCH the updated Case properties to the Salesforce REST API
Note: TODO: Add the logic to look up another Case where the TRH_WAMS_Id__c is the Parent, populate Parent_ID

FME custom transformer OwnerIdSetter
Sets the OwnerId to the appropriate User or Queue based upon the STATUS returned by Maximo.
        STATUS = REASSIGNED: set OwnerId to Re-Assigned Queue and remove STATUS from output 
        STATUS = CANCELLED: set OwnerId to Duplicate Queue and remove STATUS from output 
        All other STATUS: set OwnerId to Maximo User in Salesforce.com. Keep the STATUS in the output

Parameters:
- SalesforceMaximoUser = Integration User   # Enter the name (first and last) of the Maximo User in Salesforce
- ASSIGNEDTO = @Value(AssignedTo)   # AssignedTo
- STATUS.MEMO = @Value(Status.Memo)   # Status.Memo
- STATUS = @Value(Status)   # Status
- TARGET_REQUEST_ID = @Value(Target_Request_Id)   # Target Request Id
- PARENT_ID = @Value(Parent_Id)   # Parent Id

Input (input)
    -> TestFilter
Note: Test Returned STATUS / from Maximo
TestFilter
    DEFAULT_VALUE = Unmapped
    TEST_LIST:
      BOOL_OP,OR,COMPOSITE_TEST,<Unused>,TEST_CLAUSE,"TEST @UpperCase(@Value(Status)) = REASSIGNED",Reassigned,BOOL_OP,AND,COMPOSITE_TEST,<Unused>,TEST_CLAUSE,"TEST @UpperCase(@Value(Status)) = CLOSED
      TEST @Value(Status.Memo) ATTRIBUTE_HAS_VALUE """"",Cancelled,BOOL_OP,COMPOSITE,COMPOSITE_TEST,"""(1 OR 2) AND 3""",TEST_CLAUSE,"TEST @UpperCase(@Value(Status)) = CLOSED
      TEST @UpperCase(@Value(Status)) = DUPLICATE
      TEST @Value(Parent_Id) ATTRIBUTE_HAS_VALUE """"",Duplicate,BOOL_OP,COMPOSITE,COMPOSITE_TEST,"""(1 OR 2) AND 3""",TEST_CLAUSE,"TEST @UpperCase(@Value(Status)) = IN PROGRESS
      TEST @UpperCase(@Value(Status)) = QUEUED
      TEST @Value(AssignedTo) ATTRIBUTE_HAS_VALUE """"",Assigned
    Reassigned -> QueueNameSetter
    Cancelled -> QueueNameSetter_2
    Duplicate -> QueueNameSetter_3
    Assigned -> SalesforceConnector
    Unmapped -> Unmapped (output)
Note: If STATUS = CANCELLED or REASSIGNED or DUPLICATE Then / Set OwnerId to appropriate Queue / Set Status to NULL / Set IsReassigned or TRH_Duplicate__c flag / Else If STATUS = (IN PROGRESS or QUEUED) and ASSIGNEDTO has value Then / Set OwnerId to SF.com Maximo User / Else / Do Nothing
QueueNameSetter: AttributeCreator
    ATTR_TABLE:
      SET_TO QueueName = TRH_Re_Assign_Queue
      SET_TO IsReassigned = Yes
      SET_TO Status = FME_NULL_VALUE
      SET_TO Target_Request_Id = FME_NULL_VALUE
    -> SalesforceConnector_2
QueueNameSetter_2: AttributeCreator
    ATTR_TABLE:
      SET_TO QueueName = Cancelled_Queue
      SET_TO Status = Closed
      SET_TO CloseReason = Maximo Work Order Cancelled
    -> SalesforceConnector_2
QueueNameSetter_3: AttributeCreator
    ATTR_TABLE:
      SET_TO QueueName = TRH_Duplicate_Queue
      SET_TO Status = FME_NULL_VALUE
      SET_TO TRH_Duplicate__c = True
    -> SalesforceConnector_2
Note: TODO: It is possible that if any of the queue names in Salesforce are not the same as specified, this will return zero records and the translation will stop without warning.
SalesforceConnector_2
    API_VERSION = Latest
    CONNECTION = CRMTRHSalesforce
    INCLUDE_DELETED = NO
    NEW_ATTRS = Id
    SOQL = SELECT Id FROM Group WHERE DeveloperName = '@Value(QueueName)'
    -> AttributeRenamer_2
Note: TODO: It is possible that if the Integration User is different than the parameter SalesforceMaximoUse, this will return zero records and the translation will stop with no warning.
SalesforceConnector
    API_VERSION = Latest
    CONNECTION = CRMTRHSalesforce
    INCLUDE_DELETED = NO
    NEW_ATTRS = Id
    SOQL = SELECT Id FROM User Where Name='@Value(SalesforceMaximoUser)'
    -> AttributeRenamer_2
Note: We're only interested in retrieving the new OwnerId. Remove other attributes from the SF.com lookup. / - Rename Id to OwnerId. / - Remove Status if in Reassigned or Duplicate queue.
AttributeRenamer_2
    ATTR_TABLE = RENAME_SET_DEFAULT Id > Maximo.OwnerId
    -> BulkAttributeRenamer
BulkAttributeRenamer
    ATTRCHOICE = All Attributes
    CASE_DISP = YES
    MODE_CHOICE = RENAME
    PATTERN_ACTION_DISP = REMOVEPREFIX
    REPLACE_STR = Maximo.
    -> Mapped (output)
Mapped (output)
Unmapped (output)

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
Input Ports
    Input
Accepts any feature.
    Output Ports
    Output
Ouputs the original feature with an added attribute containing the JSON object.
    Parameters
    Attributes to Pack
    Specific attributes to pack. Chosing any attributes will disable the filter (described below).
    Filter Prefix
All attributes with this prefix will be added to the packed attribute. Leaving this value blank will pack all the attributes.
    Packed Attribute Name
The name of the new attribute containing the packed values

Parameters:
- FILTER =   # Filter Prefix (blank for all attributes)
- PACKED = _packed   # Packed Attribute Name
- ATTRS =   # " " Attributes to Pack

Input (input)
    -> ParameterFetcher
Note: Get filter value
ParameterFetcher
    ATTR_LIST = AttributeJSONPacker_FILTER {$(FILTER)} AttributeJSONPacker_PACKED {$(PACKED)} AttributeJSONPacker_ATTRS {$(ATTRS)}
    -> PythonCaller
PythonCaller
    NEW_ATTRIBUTES = $(PACKED)
    PYTHONSOURCE:
      from __future__ import absolute_import, division, print_function, unicode_literals

      import fmeobjects
      import binascii
      import json
      import six

      # This class will create a packed list of format
      # attributes suitable for use with @SupplyAttributes()

      def packIgdsAtts(feature):
         # get a list of attribute names
         attlist = feature.getAllAttributeNames()
         attlist = map(six.text_type, attlist)

         # get attributes to pack
         pack_attrs = feature.getAttribute('AttributeJSONPacker_ATTRS').replace('"', '').strip().split(',')

         # get filter value
         filter = feature.getAttribute('AttributeJSONPacker_FILTER')


         # get packed attribute name
         packedAtt = feature.getAttribute('AttributeJSONPacker_PACKED')

         addedAttrs = {
            'AttributeJSONPacker_ATTRS',
            'AttributeJSONPacker_FILTER',
            'AttributeJSONPacker_PACKED',
         }

         # disable filter if packed attribute chosen
         if pack_attrs[0] != "":
             filter = False

         # create dict for packed attributes
         packed = {}

         # loop through attribute names
         for att in attlist:
             if ((filter and filter in att) or att in pack_attrs) and att not in addedAttrs:
                 att_value = feature.getAttribute(att)
                 float_val, int_val = None, None
                 try:
                     float_val = float(att_value)
                     int_val = int(att_value)
                     if int_val == float_val:
                         att_value = int_val
                     else:
                         att_value = float_val
                 except ValueError as e:
                     if int_val is not None:
                         att_value = int_val
                     if float_val is not None:
                         att_value = float_val

                 # convert binary attributes to hex for storage
                 if type(att_value) == bytearray:
                     att_value = "0x" + binascii.hexlify(att_value)
                 # append attribute value
                 packed[att] = att_value

         #add packed attributes in JSON format
         feature.setAttribute(packedAtt,json.dumps(packed,separators=(',', ':'), ensure_ascii=False))
    PYTHONSYMBOL = packIgdsAtts
    -> Output (output)
Output (output)
